module rfc8561-nc-1.0 {
  yang-version 1.1;
  namespace "http://tail-f.com/ns/ned-id/rfc8561-nc-1.0";
  prefix rfc8561-nc-1.0;

  import rfc8561-nc {
    prefix family;
  }

  identity rfc8561-nc-1.0 {
    base family:rfc8561-nc;
  }
}
