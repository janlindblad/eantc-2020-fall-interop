module rfc8561-nc {
  yang-version 1.1;
  namespace "http://tail-f.com/ns/ned-id/rfc8561-nc";
  prefix rfc8561-nc;

  import tailf-common {
    prefix tailf;
  }

  import tailf-ncs-ned {
    prefix ned;
  }

  identity rfc8561-nc {
    tailf:abstract;
    base ned:netconf-ned-id;
  }
}
