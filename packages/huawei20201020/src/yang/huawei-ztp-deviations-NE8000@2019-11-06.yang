/*
Copyright (C) 2019 Huawei Technologies Co., Ltd. All rights reserved.
*/
module huawei-ztp-deviations-NE8000 {
  namespace "urn:huawei:yang:huawei-ztp-deviations-NE8000";
  prefix ztp-devs-NE8000;

  import huawei-ztp {
    prefix ztp;
  }

  organization
    "Huawei Technologies Co., Ltd.";

  contact
    "Huawei Industrial Base
     Bantian, Longgang
     Shenzhen 518129
     People's Republic of China
     Website: http://www.huawei.com
     Email: support@huawei.com";

  description
    "This module defines deviation statements for huawei-ztp module.";

  revision 2019-11-06 {
    description
      "Initial revision.";
    reference
      "Huawei private.";
  }

  deviation "/ztp:ztp/ztp:status/ztp:pre-configuration-name" {
    deviate not-supported;
  }
  deviation "/ztp:set-pre-configuration" {
    deviate not-supported;
  }
  deviation "/ztp:reset-pre-configuration" {
    deviate not-supported;
  }

}
