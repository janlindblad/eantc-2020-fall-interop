/*
Copyright (C) 2019-2020 Huawei Technologies Co., Ltd. All rights reserved.
*/
module huawei-bgp {
  namespace "urn:huawei:yang:huawei-bgp";
  prefix bgp;
  import huawei-extension {
    prefix ext;
  }
  import ietf-inet-types {
    prefix inet;
  }
  import ietf-yang-types {
    prefix yang;
  }
  import huawei-network-instance {
    prefix ni;
  }
  import huawei-ifm {
    prefix ifm;
  }
  import huawei-pub-type {
    prefix pub-type;
  }
  import huawei-routing-policy {
    prefix rtp;
  }
  import huawei-xpl {
    prefix xpl;
  }
  import huawei-routing {
    prefix rt;
  }
  import huawei-tunnel-management {
    prefix tnlm;
  }
  include huawei-bgp-type;
  include huawei-bgp-common;
  organization
    "Huawei Technologies Co., Ltd.";
  contact
    "Huawei Industrial Base
     Bantian, Longgang
     Shenzhen 518129
     People's Republic of China
     Website: http://www.huawei.com
     Email: support@huawei.com";
  description
    "Inter-AS routing protocol that exchanges Network Layer Reachability Information (NLRI) with other BGP systems.";
  revision 2020-02-25 {
    description
      "The YANG descriptions are modified according to new standards.";
    reference "Huawei private.";
  }
  revision 2019-03-22 {
    description
      "Initial revision.";
    reference
      "Huawei private.";
  }
  ext:task-name  "bgp";
  
  /*
   * grouping-stmt
   */
  grouping unicast-aggregate-routes-type {
    description
      "BGP IPv4/IPv6 unicast aggregate routes.";
    leaf address {
      type inet:ip-address-no-zone;
      description
        "Specify the IPv4 address or IPv6 address of a summarized route. Only IPv4 summarized routes can be configured in the IPv4 address family and only IPv6 summarized routes can be configured in the IPv6 address family.";
    }
    leaf mask-length {
      type uint8 {
        range "0..128";
      }
      description
        "Specify the mask length of a summarized address. The mask length ranges from 0 to 32 for an IPv4 address, and ranges from 0 to 128 for an IPv6 address.";
    }
    leaf as-set {
      type boolean;
      default "false";
      description
        "Enable/disable the generation of routes with the AS-SET attribute. This option can be used to create a summarized route. The AS_Path attribute of the summarized route contains the AS-Path attributes of the specific routes for the route summarization. Exercise caution when using this option if multiple AS_Paths need to be summarized to prevent route flapping.";
    }
    leaf detail-suppressed {
      type boolean;
      default "false";
      description
        "Enable/disable detail-suppressed. Suppress the advertisement of specific routes for the route summarization. Only the summarized route is advertised.";
    }
    choice policy-type {
      description
        "Set route policy or filter.";
      case rtp-ref {
        description
          "Route policy.";
        leaf attribute-policy {
          type leafref {
            path "/rtp:routing-policy/rtp:policy-definitions/rtp:policy-definition/rtp:name";
          }
          description
            "Specify an attribute of summarized routes. If apply as-path is used to configure the AS_Path attribute that is used in the route Summarization policy, and the as-set keyword is set, the AS_Path attribute in the policy does not take effect. This parameter and any of the following parameters overwrite each other: suppressFilter, originFilter, and attributeFilter.";
        }
        leaf origin-policy {
          type leafref {
            path "/rtp:routing-policy/rtp:policy-definitions/rtp:policy-definition/rtp:name";
          }
          description
            "Specify the name of a policy for generating summarized routes. Summarized routes are generated only when the routes match route-policy. This parameter and any of the following parameters overwrite each other: suppressFilter, originFilter, and attributeFilter.";
        }
        leaf suppress-policy {
          type leafref {
            path "/rtp:routing-policy/rtp:policy-definitions/rtp:policy-definition/rtp:name";
          }
          description
            "Specify a policy for suppressing the advertisement of specified routes. The routes matching the policy are not advertised, and other routes are advertised. This parameter and any of the following parameters overwrite each other: suppressFilter, originFilter, and attributeFilter.";
        }
      }
    }
  }
  grouping network-route-ipv4 {
    description
      "BGP network routes.";
    leaf address {
      type inet:ipv4-address-no-zone;
      description
        "Specify the IP address advertised by BGP. An IPv4 address can be configured in the IPv4 address family. Note: During the configuration of a network route, the IP address is adjusted based on the mask. It is recommended that you click Synchronize All after creating a network route.";
    }
    leaf mask-length {
      type uint8 {
        range "0..32";
      }
      description
        "Specify the mask length of an IP address. The mask length ranges from 0 to 32 for an IPv4 address.";
    }
    uses choice-policy-set {
      refine policy-type {
        description
          "Specify the route-policy or filter for route advertisement.";
      }
    }
  }
  grouping network-route-ipv6 {
    description
      "BGP network routes.";
    leaf address {
      type inet:ipv6-address-no-zone;
      description
        "Specify the IP address advertised by BGP. An IPv6 routes can be configured in the IPv6 address family. Note: During the configuration of a network route, the IP address is adjusted based on the mask. It is recommended that you click Synchronize All after creating a network route.";
    }
    leaf mask-length {
      type uint8 {
        range "0..128";
      }
      description
        "Specify the mask length of an IP address. The mask length ranges from 0 to 128 for an IPv6 address.";
    }
    uses choice-policy-set {
      refine policy-type {
        description
          "Specify the route-policy or filter for route advertisement.";
      }
    }
  }
  grouping advertise-route-to-evpn-type {
    description
      "Advertise-routes-type configuration.";
    list advertise-route-to-evpn {
      key "protocol";
      description
        "Configure the advertise route protocol.";
      leaf protocol {
        type enumeration {
          enum "all" {
            value 0;
            description
              "Advertise all the types of route protocol.";
          }
        }
        description
          "Route protocol.";
      }
      leaf import-multipath {
        type boolean;
        default "false";
        description
          "Enable/disable route import from multiple paths.";
      }
      leaf advertise-route-mode {
        type enumeration {
          enum "all" {
            value 0;
            description
              "All:";
          }
          enum "best" {
            value 1;
            description
              "Best:";
          }
          enum "valid" {
            value 2;
            description
              "Valid:";
          }
        }
        default "all";
        description
          "VPN advertise route mode to evrf.";
      }
    }
  }
  grouping vpn-target-type {
    description
      "BGP IPv4/IPv6 VPN target.";
    leaf policy-vpntarget {
      type boolean;
      default "true";
      description
        "Enable/disable VPN target-based filtering for the received VPN routes. Only the VPN route whose Export RT attribute matches the local Import RT attribute can be added to the routing table. This option can be used in the inter-AS VPN Option B solution and the ASBR MP-EBGP inter-AS L2VPN solution in Kompella mode.";
    }
  }
  grouping reflector-cluster-type {
    description
      "BGP reflector cluster-id.";
    choice reflector-type {
      description
        "Set IPv4 address or id.";
      case address {
        description
          "IPv4 address.";
        leaf reflector-cluster-ipv4 {
          type inet:ipv4-address-no-zone;
          description
            "Set a cluster ID. The value is expressed in the format of an IPv4 address. Configuring multiple RRs in a cluster can enhance the stability of the network. If a cluster has more than one RR, select this option to set the same cluster ID for all the RRs to avoid routing loops. To allow clients to receive routes from RRs, ensure that the cluster ID of the RRs is different from the router ID of any client. If the cluster ID of the RRs is the same as the router ID of a client, the client will discard received routes.";
        }
      }
      case id {
        description
          "Set value.";
        leaf reflector-cluster-id {
          type uint32 {
            range "1..4294967295";
          }
          description
            "Set a cluster ID. Configuring multiple RRs in a cluster can enhance the stability of the network. If a cluster has more than one RR, select this option to set the same cluster ID for all the RRs to avoid routing loops. To allow clients to receive routes from RRs, ensure that the cluster ID of the RRs is different from the router ID of any client. If the cluster ID of the RRs is the same as the router ID of a client, the client will discard received routes.";
        }
      }
    }
  }
  grouping reflect-type {
    description
      "Set reflect client or change path-attribute.";
    leaf reflect-change-path {
      type boolean;
      default "false";
      description
        "Enable/disable an RR to use an export policy to change route AS_Path.";
    }
  }
  grouping bfd-detect-parameter-type {
    description
      "BFD detect parameter configuration.";
    leaf multiplier {
      type uint32 {
        range "3..50";
      }
      default "3";
      description
        "Specify the detection multiplier.";
    }
    leaf min-rx-interval {
      type uint32 {
        range "3..1000";
      }
      units "ms";
      description
        "Specify the minimum interval at which BFD packets are received. By default, the value is determined by the PAF file.";
    }
    leaf min-tx-interval {
      type uint32 {
        range "3..1000";
      }
      units "ms";
      description
        "Specify the minimum interval at which BFD packets are sent. By default, the value is determined by the PAF file.";
    }
  }
  grouping group-entropy-label-type {
    description
      "Entropy label parameter configuration in a peer group.";
    leaf advertise-entropy-label {
      type boolean;
      default "false";
      description
        "Enable/disable the capability of advertising entropy labels.";
    }
    leaf padding {
      when "../advertise-entropy-label='true'";
      type string {
        length "1..32";
        pattern '(([0-9A-F])*)';
      }
      description
        "Padding format. The value is a hexadecimal string containing 1 to 32 characters (16 hexadecimal numbers). It cannot contain spaces, and can only contain uppercase letters (A to F) and digits (0 to 9), and the length must be an even number.";
    }
    leaf attribute-type {
      when "../advertise-entropy-label='true'";
      type entropy-label-attribute-type;
      mandatory true;
      description
        "The attribute-type of advertising entropy labels.";
    }
    leaf entropy-label {
      type boolean;
      default "false";
      description
        "Enable/disable the function of delivering the entropy label capability to the forwarding plane.";
    }
  }
  grouping peer-entropy-label-type {
    description
      "Entropy label parameter configuration in a peer.";
    leaf advertise-entropy-label {
      type peer-comm-config-type;
      default "default";
      description
        "Enable the capability of advertising entropy labels.";
    }
    leaf padding {
      when "../advertise-entropy-label='enable'";
      type string {
        length "1..32";
        pattern '(([0-9A-F])*)';
      }
      description
        "Padding format. The value is a hexadecimal string containing 1 to 32 characters (16 hexadecimal numbers). It cannot contain spaces, and can only contain uppercase letters (A to F) and digits (0 to 9), and the length must be an even number.";
    }
    leaf attribute-type {
      when "../advertise-entropy-label='enable'";
      type entropy-label-attribute-type;
      mandatory true;
      description
        "The attribute-type of advertising entropy labels.";
    }
    leaf entropy-label {
      type peer-comm-config-type;
      default "default";
      description
        "Enable the function of delivering the entropy label capability to the forwarding plane.";
    }
    leaf effect-advertise-entropy-label {
      type boolean;
      default "false";
      config false;
      description
        "Whether the capability of advertising entropy labels is enabled on the BGP peer.";
    }
    leaf effect-padding {
      when "../effect-advertise-entropy-label='true'";
      type string {
      length "1..32";
        pattern '(([0-9A-F])*)';
      }
      config false;
      description
        "Padding format.";
    }
    leaf effect-attribute-type {
      when "../effect-advertise-entropy-label='true'";
      type entropy-label-attribute-type;
      config false;
      description
        "The attribute-type of advertising entropy labels.";
    }
    leaf effect-entropy-label {
      type boolean;
      default "false";
      config false;
      description
        "Whether the function of delivering the entropy label capability to the forwarding plane is enabled on the BGP peer.";
    }
  }
  container bgp {
    description
      "Inter-AS routing protocol that exchanges Network Layer Reachability Information (NLRI) with other BGP systems,
      Universal BGP configurations that contain the basic BGP configurations and the query information.";
    container global {
      description
        "Configure the router for BGP globally.";
      leaf yang-enable {
        type boolean;
        default "false";
        description
          "Enable/disable BGP yang mode. To use NETCONF YANG to manage BGP VPN instances in huawei-bgp.yang, enable YANG management for the BGP VPN instances on the device or enable the leaf node globally in the huawei-bgp.yang file.";
      }
    }
    container paf-controls {
      description
        "List of PAF-based limiting disabled for some features.";
      list paf-control {
        key "feature-name";
        description
          "Configure PAF-based limiting disabled for some features.";
        leaf feature-name {
          type paf-control-feature-type;
          description
            "Feature name.";
        }
      }
    }
    container base-process {
      description
        "Configure the global BGP information, such as the protocol version, AS number, and system identifier.";
      leaf enable {
        type boolean;
        must "(../enable='true' and ../as) or (../enable='false' and not(../as))";
        default "false";
        description
          "Enable/disable BGP function.";
      }
      leaf as {
        when "../enable='true'";
        type as-number-validate;
        description
          "Local AS number, which can be in either of the two formats:
           The two-byte format is X. X is an integer ranging from 1 to 65535.
           The four-byte format is X.Y and X. When the format is X.Y, X and Y are both integers, with the value of X ranging from 1 to 65535, and the value of Y ranging from 0 to 65535; when the format is X, X is an interger, with the value ranging from 1 to 4294967295.
           An AS consists of multiple routers managed based on the same techniques. Interior Gateway Protocol (IGP) and universal routing metric packets are used inside an AS, and Exterior Gateway Protocol (EGP) is used outside to send packets to other ASs. With the development of this definition, one AS usually uses multiple IGPs and metrics. Even though multiple IGPs and metrics are used, the routing plan and destination reachability of an AS are consistent with those of another AS. The local AS number cannot be configured same as the confederation sub-ASs. The object cannot be deleted or modified.";
        ext:operation-exclude update {
          description "The node cannot be modified when BGP is enabled.";
        }
      }
      leaf keep-all-routes {
        when "../enable='true'";
        type boolean;
        default "false";
        description
          "Enable/disable saving all the updated information about BGP routes from a peer or peer group after a BGP connection is established, even though these BGP routes fail to match the routing policy on the ingress. Save all the updated information about BGP routes from a peer or peer group after a BGP connection is established, even though these BGP routes fail to match the routing policy on the ingress. By default, only the updated information about BGP routes from a specified peer is saved on condition that the routes match the routing policy on the ingress. If a router supports route refreshing, this option is not required.";
      }
      leaf check-first-as {
        when "../enable='true'";
        type boolean;
        default "true";
        description
          "Enable/disable checking the first AS in the AS_Path of the update messages from EBGP peers.";
      }
      leaf router-id-auto-select {
        when "../enable='true'";
        type boolean;
        default "false";
        description
          "Enable/disable router ID auto select. If a BGP VPN instance is not enabled to select a router ID, a router ID can be configured for the BGP VPN instance. If no router ID is configured for the BGP VPN instance, the BGP VPN instance inherits the router ID of the public network instance. If a BGP VPN instance is enabled to select a router ID, it uses the address of an interface bound to a VPN as the router ID based on the following rules: 
          1. If Loopback interfaces configured with IP addresses exist, the largest IP address among the IP addresses of the Loopback interfaces is selected as the router ID. 
          2. If there is no Loopback interface configured with an IP address, the largest IP address among the IP addresses of other interfaces is selected as the router ID, regardless of whether the interface is Up.";
      }
      leaf shutdown {
        when "../enable='true'";
        type boolean;
        default "false";
        description
          "Enable/disable interrupting BGP all neighbour.";
      }
      leaf local-ifnet-mtu {
        when "../enable='true'";
        type uint16 {
          range "46..65535";
        }
        default "1500";
        description
          "BGP LOCALIFNET MTU.";
      }
      leaf private-4byte-as {
        when "../enable='true'";
        type boolean;
        default "false";
        description
          "Enable/disable BGP private 4 byte AS. With BGP private-4-byte-as, BGP private as is from 64512 to 65535 and from 4200000000 to 4294967294.";
      }
      leaf local-cross-no-med {
        when "../enable='true'";
        type boolean;
        default "false";
        description
          "Enable/disable local cross routing non-med.";
      }
      leaf as-path-limit {
        when "../enable='true'";
        type uint16 {
          range "1..2000";
        }
        description
          "Maximum number of AS numbers in the AS_Path attribute.";
      }
      container confederation {
        when "../enable='true'";
        description
          "Configure confederation.";
        leaf id {
          type as-number-validate;
          description
            "Configure the confederation ID.";
        }
        leaf nonstanded {
          type boolean;
          default "false";
          description
            "Enable/disable nonstanded. Configure the device to be compatible with devices in a nonstandard confederation.";
        }
        leaf-list as {
          when "../id";
          type as-number-validate;
          max-elements 32;
          description
            "Configure the confederation AS number. The confederation AS number can be in either of the two formats:
            The two-byte format is X. X is an integer ranging from 1 to 65535.
            The four-byte format is X.Y and X. When the format is X.Y, X and Y are both integers, with the value of X ranging from 1 to 65535, and the value of Y ranging from 0 to 65535; when the format is X, X is an interger, with the value of X ranging from 1 to 4294967295. The confederation sub-ASs cannot be configured same as the local AS number.";
        }
      }
      container graceful-restart {
        when "../enable='true'";
        description
          "Configure the graceful-restart.";
        leaf enable {
          type boolean;
          default "false";
          description
            "Enable/disable GR of the BGP speaker in the specified address family, peer address, or peer group. When GR is enabled, the BGP speaker enabled with GR keeps the forwarding state and sends the End-Of-RIB flag during the restart. In this case, however, the BGP speaker may not maintain the forwarding table. Enabling or disabling GR may delete and re-establish all sessions and instances.";
        }
        leaf time-wait-for-rib {
          type uint32 {
            range "3..3000";
          }
          units "s";
          default "600";
          description
            "Period of waiting for the End-Of-RIB flag. The value is an integer. When a BGP session is established or re-established, the router enabled with GR should receive the End-Of-RIB flag in this period. If the router does not receive the End-Of-RIB flag in this period, ensure that the router can exit from the GR process.";
        }
        leaf restart-time {
          type uint16 {
            range "3..3600";
          }
          units "s";
          default "150";
          description
            "Specifies the maximum time during which a peer waits for a BGP session reestablishment.";
        }
        leaf peer-reset {
          type boolean;
          default "false";
          description
            "Enable/disable peer disconnection through GR.";
        }
      }
      container remote-prefix-sid-states {
        config false;
        description
          "List of remote prefix SID.";
        list remote-prefix-sid-state {
          key "prefix-sid";
          description
            "Operational state of the remote BGP prefix SID.";
          leaf prefix-sid {
            type inet:ipv6-address-no-zone;
            description
              "Prefix SID value.";
          }
          leaf locator-sid {
            type inet:ipv6-address-no-zone;
            description
              "Prefix SID value of the mirrored locator.";
          }
          leaf locator-mask-length {
            type uint8 {
              range "0..128";
            }
            description
              "Mask length of the SID of the mirrored locator.";
          }
          leaf vpn-name {
            type string {
              length "1..31";
            }
            description
              "Name of the VPN instance that contains the prefix SID.";
          }
        }
      }
      container reference-period {
        when "../enable='true'";
        must "hold-interval>suppress-interval";
        must "clear-interval>hold-interval";
        description
          "Configure the reference period.";
        leaf suppress-interval {
          type uint32 {
            range "1..65535";
          }
          units "s";
          default "60";
          description
            "Specifies the reference period used to add penalty in case of next hop flapping.";
        }
        leaf hold-interval {
          type uint32 {
            range "1..65535";
          }
          units "s";
          default "120";
          description
            "Specifies the reference period used to hold penalty in case of next hop flapping.";
        }
        leaf clear-interval {
          type uint32 {
            range "1..65535";
          }
          units "s";
          default "600";
          description
            "Specifies the reference period used to clear penalty in case of next hop flapping.";
        }
      }
      container timer {
        when "../enable='true'";
        description
          "Configure BGP global timer parameters.";
        uses global-timer-para-type;
      }
      container graceful-restart-status {
        config false;
        description
          "Statistics of the GR status of a BGP speaker.";
        leaf enable {
          type boolean;
          description
            "The GR capability of a BGP speaker.";
        }
        leaf restart-timer {
          type uint32;
          units "s";
          description
            "Period during which a BGP speaker waits for the peer relationship reestablishment.";
        }
        leaf eor-timer {
          type uint32;
          units "s";
          description
            "Period during which a BGP speaker waits for the End-Of-RIB flag.";
        }
        container peers {
          description
            "List of display the GR statistics for a BGP peer.";
          list peer {
            key "vpn-name af address";
            description
              "Statistics of the GR status of a BGP peer.";
            leaf vpn-name {
              type string {
                length "1..31";
              }
              description
                "VPN name of a BGP instance.";
            }
            leaf af {
              type string {
                length "1..300";
              }
              description
                "BGP address-family type.";
            }
            leaf address {
              type inet:ip-address-no-zone;
              description
                "Address of a peer.";
            }
            leaf peer-capability {
              type string {
                length "1..300";
              }
              description
                "GR capability of a neighbor.";
            }
            leaf gr-capability-enable {
              type boolean;
              description
                "Whether GR capability is negotiated.";
            }
            leaf bgp-peer-state {
              type bgp:peer-state-type;
              description
                "Status of the peer.";
            }
            leaf gr-state {
              type boolean;
              description
                "GR status of a neighbor.";
            }
            leaf restart-left-timer {
              type uint32;
              units "s";
              description
                "Restart left timer.";
            }
            leaf eor-sent {
              type boolean;
              description
                "Whether error is sent.";
            }
            leaf stale-route-num {
              type uint32;
              description
                "Stale route number.";
            }
          }
        }
      }
      container error-discard-info {
        config false;
        description
          "Statistics of BGP error message.";
        leaf cluster-id-loop-count {
          type uint32;
          description
            "Count of routes discarded because cluster IDs are the same.";
        }
        leaf receive-as-over-limit-count {
          type uint32;
          description
            "Count of received routes discarded because the number of AS numbers in the AS_Path exceeds the upper limit.";
        }
        leaf advertise-as-over-limit-count {
          type uint32;
          description
            "Count of advertised routes discarded because the number of AS numbers in the AS_Path exceeds the upper limit.";
        }
        leaf as-loop-count {
          type uint32;
          description
            "Count of routes discarded because AS numbers are the same.";
        }
        leaf zero-rd-count {
          type uint32;
          description
            "Count of routes discarded because of the RD 0:0.";
        }
        leaf no-prefix-count {
          type uint32;
          description
            "Count of routes discarded because no prefix exists.";
        }
        leaf path-attribute-error-count {
          type uint32;
          description
            "Count of routes with error path attributes.";
        }
        leaf originator-id-loop-count {
          type uint32;
          description
            "Count of routes with an Originator ID conflict.";
        }
        leaf md5-count {
          type uint32;
          description
            "MD5 count.";
        }
        container afs {
          description
            "List of BGP routes discarded in the address family.";
          list af {
            key "address-family";
            description
              "Statistics of BGP route discarded in the address family.";
            leaf address-family {
              type bgp:af-type;
              description
                "Address family type.";
            }
            leaf cluster-id-loop-count {
              type uint32;
              description
                "Count of routes discarded because cluster IDs are the same.";
            }
            leaf receive-as-over-limit-count {
              type uint32;
              description
                "Count of received routes discarded because the number of AS numbers in the AS_Path exceeds the upper limit.";
            }
            leaf advertise-as-over-limit-count {
              type uint32;
              description
                "Count of advertised routes discarded because the number of AS numbers in the AS_Path exceeds the upper limit.";
            }
            leaf as-loop-count {
              type uint32;
              description
                "Count of routes discarded because AS numbers are the same.";
            }
            leaf zero-rd-count {
              type uint32;
              description
                "Count of routes discarded because of the RD 0:0.";
            }
            leaf path-attribute-error-count {
              type uint32;
              description
                "Count of routes discarded because no prefix exists.";
            }
            leaf originator-id-loop-count {
              type uint32;
              description
                "Count of routes with an Originator ID conflict.";
            }
            leaf peer-record-count {
              type uint32;
              description
                "Peer record count.";
            }
            container peers {
              description
                "List of BGP peer error information.";
              list peer {
                key "vpn-name address";
                description
                  "Statistics of BGP peer error information. The display error discard command displays statistics about all address families and packets discarded by peers. The NMS supports query based on the following filtering modes: 
                  (1) Statistics query about the specified address family and statistics about the packets discarded by peers. Such query is not supported by the preceding command.
                  (2) Query of the information about the discarded packets filtered based on the specified peer or VPN instance. The query result is different from that in the command output. The command displays the statistics of the address family in which packet loss occurs and the information about the packets discarded by the peer.";
                leaf vpn-name {
                  type string {
                    length "1..31";
                  }
                  description
                    "VPN name.";
                }
                leaf address {
                  type inet:ip-address-no-zone;
                  description
                    "Peer address.";
                }
                leaf record-time {
                  type yang:date-and-time;
                  description
                    "Record time.";
                }
                leaf reason {
                  type string {
                    length "1..300";
                  }
                  description
                    "Packet loss reason.";
                }
                leaf error-data {
                  type string {
                    length "1..300";
                  }
                  description
                    "Error data.";
                }
                leaf vpn-id {
                  type uint32;
                  description
                    "VPN index.";
                }
              }
            }
          }
        }
      }
      container vpn-brief-infos {
        config false;
        description
          "List of BGP VPN brief informations.";
        list vpn-brief-info {
          key "vpn-name address-family";
          description
            "Statistics of VPN brief information.";
          leaf vpn-name {
            type leafref {
              path "/ni:network-instance/ni:instances/ni:instance/ni:name";
            }
            description
              "VPN name of a BGP instance.";
          }
          leaf address-family {
            type bgp:af-type;
            description
              "Address family type.";
          }
          uses vpn-brief-num-type;
        }
      }
    }
  }
  /*
   * augment-stmt
   */
  augment "/ni:network-instance/ni:instances/ni:instance" {
    description
      "BGP network instance configuration.";
    container bgp {
      description
        "Configure BGP network instance. All nodes of private VPN Instance in this container can be used only when the value of the global BGP enabling node (/bgp:bgp/bgp:global/bgp:yang-enable) is set to true.";
      container base-process {
        when "/bgp:bgp/bgp:base-process/bgp:enable='true'";
        presence "Create vrf session.";
        description
          "Enable/disable BGP instances. The _public_ instance cannot be deleted.";
        ext:generated-by system {
          when "../../ni:name = '_public_'";
          description "The public instances is generated automatically when BGP is enabled.";
        }
        ext:operation-exclude create|delete {
          when "../../ni:name = '_public_'";
          description "The public instance cannot be manually created or deleted.";
        }
        leaf router-id {
          type inet:ipv4-address-no-zone;
          description
            "ID of a router that is in IPv4 address format. Certain dynamic routing protocols require a router ID. If no router ID is specified for a router when these protocols are enabled, the router ID in the RM module is used by default. The default router ID in the RM module is 0.0.0.0 when the router is not configured with any interface. 
             The rules for selecting a router ID are as follows:
             1. If you set a router ID through this configuration, the set router ID is used. If the router ID is not set, you need to select a router ID according to the following rules:
             (1) If loopback interfaces configured with IP addresses exist, the largest IP address among the IP addresses of the loopback interfaces is selected as the router ID.
             (2) If no loopback interface configured with an IP address exists, the largest IP address among the IP addresses of other interfaces is selected as the router ID, regardless of whether the interface is Up.
             The router ID is reselected only when the interface address that is selected as the router ID is deleted or changed. The router ID is not reselected in any of the following cases:
             a. The interface is Down.
             b. A loopback interface is configured when the IP address of a non-loopback interface is selected as the router ID.
             c. A larger IP address of an interface is configured.
             2. Each VPN instance selects the router ID from the addresses of the interfaces of the VPN instance according to the preceding rules.
             3. When both the AMB and SMB exist on the router, the system backs up the router ID set through the related command and the router ID that is selected from IP addresses of the interfaces. After the active/standby switchover is performed, the system checks the validity of the router ID selected from the interface addresses. If the router ID is invalid, the system reselects a router ID.";
        }
        leaf router-id-auto-select {
          when "../../../ni:name!='_public_'";
          type boolean;
          must "../router-id-auto-select!='true' or (../router-id-auto-select='true' and not (../router-id))";
          default "false";
          description
            "Enable/disable router ID auto select. If a BGP VPN instance is not enabled to select a router ID, a router ID can be configured for the BGP VPN instance. If no router ID is configured for the BGP VPN instance, the BGP VPN instance inherits the router ID of the public network instance. If a BGP VPN instance is enabled to select a router ID, it uses the address of an interface bound to a VPN as the router ID based on the following rules:

            1. If Loopback interfaces configured with IP addresses exist, the largest IP address among the IP addresses of the Loopback interfaces is selected as the router ID.

            2. If there is no Loopback interface configured with an IP address, the largest IP address among the IP addresses of other interfaces is selected as the router ID, regardless of whether the interface is Up.";
        }
        leaf effect-router-id {
          type inet:ipv4-address-no-zone;
          default "0.0.0.0";
          config false;
          description
            "Router ID that takes effect.";
        }
        container afs {
          description
            "List of BGP address family instances.";
          list af {
            key "type";
            description
              "Configure BGP address family instance. In public network instances, all types of address families can be configured. In IPv4 VPN instances, the IPv4 unicast, IPv4 flow, and IPv4 labeled unicast address families can be configured. In IPv6 VPN instances, the IPv6 unicast and IPv6 flow address families can be configured. The IPv4 address family in the BGP _public_ VPN instance cannot be deleted.";
            ext:generated-by system {
              when "../../../../ni:name = '_public_'";
              ext:filter "type = 'ipv4uni'";
              description "The public instances is generated automatically when BGP is enabled.";
            }
            ext:operation-exclude create|delete {
              when "../../../../ni:name = '_public_'";
              ext:filter "type = 'ipv4uni'";
              description "The public instance cannot be manually created or deleted.";
            }
            leaf type {
              type bgp:af-type;
              description
                "Address family type of a BGP instance.";
            }
            container ipv4-unicast {
              when "../type = 'ipv4uni'";
              description
                "Configure IPv4 unicast options.";
              container common {
                description
                  "Configure IPv4 unicast common options.";
                leaf auto-frr {
                  type boolean;
                  default "false";
                  description
                    "Enable/disable BGP Auto FRR. If IP FRR, VPN FRR, and Auto FRR are all enabled, IP FRR and VPN FRR take precedence over Auto FRR. If a route fails to match the routing policy of IP FRR or VPN FRR, Auto FRR takes effect.";
                }
                leaf tunnel-selector-name {
                  when "../../../../../../../ni:name='_public_'";
                  type leafref {
                    path "/rtp:routing-policy/rtp:tunnel-selectors/rtp:tunnel-selector/rtp:name";
                  }
                  description
                    "Configure a tunnel selector and apply it to the BGP IPv4 unicast, BGP VPNv4 address families and BGP VPNv6 address families so that IPv4,VPNv4 and VPNv6 labeled routes can be iterated to tunnels based on the tunnel selector. By default, no tunnel selector is configured.";
                }
                leaf route-select-delay {
                  type uint16 {
                    range "0..3600";
                  }
                  units "s";
                  default "0";
                  description
                    "Route selection delay.";
                }
                uses reflector-cluster-type;
                uses reflect-type;
                leaf maximum-load-balancing-ibgp {
                  type uint16 {
                    range "1..65535";
                  }
                  must "not (../maximum-load-balancing>1 or ../maximum-load-balancing-eibgp or ../load-balancing-eibgp-enable='true') or ../maximum-load-balancing-ibgp=1";
                  default "1";
                  description
                    "Specify the maximum number of equal-cost IBGP routes.";
                }
                leaf maximum-load-balancing-ebgp {
                  type uint16 {
                    range "1..65535";
                  }
                  must "not (../maximum-load-balancing>1 or ../maximum-load-balancing-eibgp or ../load-balancing-eibgp-enable='true') or ../maximum-load-balancing-ebgp=1";
                  default "1";
                  description
                    "Specify the maximum number of equal-cost EBGP routes.";
                }
                leaf nexthop-select-depend-type {
                  when "../../../../../../../ni:name='_public_'";
                  type select-depend-type;
                  default "depend-ip";
                  description
                    "Specify the route iteration mode: IP or tunnel. In tunnel mode, the labeled BGP IPv4 route can participate in route selection only after its next hop is iterated to an LSP. In IP 
                    mode, the labeled BGP IPv4 route can participate in route selection only after its next hop is iterated to an IP address. By default, the labeled BGP IPv4 route can participate in route selection 
                    if its next hop can be iterated to an IP address, regardless of whether the LSP of the next hop exists. This allows the RR that is not enabled with MPLS to forward labeled routes. In non-RR 
                    networking or RR networking where the BGP next hop is changed, BGP needs to check whether there is an LSP destined for the next hop. If such an LSP is not found, BGP needs to establish an LSP in 
                    advance. If the default setting is adopted, a labeled BGP IPv4 unicast route may be selected prior to LSP establishment. As a result, services are incorrectly switched before LSP establishment and 
                    service stability is affected. Therefore, allow route selection only after the labeled BGP IPv4 route is iterated to an LSP.";
                }
                leaf nexthop-inherit-ip-cost {
                  when "../nexthop-select-depend-type='depend-tunnel'";
                  type boolean;
                  default "false";
                  description
                    "Enable/disable next hop iteration mode to IP. Specify the route iteration mode: IP or tunnel. In tunnel mode, the labeled BGP IPv4 route can participate in route selection only after its next hop is iterated to an LSP.";
                }
                leaf nexthop-resolve-aigp {
                  when "../../../../../../../ni:name!='_public_'";
                  type boolean;
                  default "false";
                  description
                    "Enable/disable route with AIGP attribute for route selection.";
                }
                leaf always-compare-med {
                  type boolean;
                  default "false";
                  description
                    "Enable/disable BGP to compare the MEDs of routes from peers in different ASs in route selection. If 
                    there are multiple reachable routes to the same destination, the route with the smallest MED is preferred. Do not use this option unless different ASs use the same IGP and route selection mode.";
                }
                leaf default-med {
                  type uint32;
                  default "0";
                  description
                    "Specify the Multi-Exit-Discriminator (MED) of BGP routes. The value is an integer. This value is valid only for the imported routes and BGP summarized routes on the local router.";
                }
                leaf summary-automatic {
                  type boolean;
                  default "false";
                  description
                    "Enable/disable automatic summarization for imported routes. Manual summarization takes precedence over automatic summarization. After automatic summarization is enabled, BGP summarizes routes based on the natural network segment (for example, 10.1.1.1/24 and 10.2.1.1/24 are summarized into 10.0.0.0/8, a Class A address), and sends only the summarized route to peers. This reduces the number of routes.";
                }
                leaf nexthop-third-party {
                  type boolean;
                  default "false";
                  description
                    "Enable/disable BGP third-party next hop.";
                }
                leaf best-route-bit-error-detection {
                  when "../../../../../../../ni:name!='_public_'";
                  type boolean;
                  default "false";
                  description
                    "Enable/disable the function to reroute traffic when a bit error event occurs.";
                }
                leaf supernet-unicast-advertise {
                  type boolean;
                  default "false";
                  description
                    "Enable/disable the function to advertise supernet unicast routes.";
                }
                leaf supernet-label-advertise {
                  type boolean;
                  default "true";
                  description
                    "Enable/disable the function to advertise supernet labeled routes.";
                }
                leaf lsp-mtu {
                  when "../../../../../../../ni:name='_public_'";
                  type uint16 {
                    range "46..65535";
                  }
                  default "1500";
                  description
                    "BGP LSP MTU.";
                }
                leaf label-free-delay {
                  type uint8 {
                    range "0..180";
                  }
                  units "s";
                  default "0";
                  description
                    "Label Free Delay.";
                }
                leaf bestroute-med-confederation {
                  when "../../../../../../../ni:name='_public_'";
                  type boolean;
                  default "false";
                  description
                    "Enable/disable BGP to compare MED value only within the federation.";
                }
                leaf bestroute-as-path-ignore {
                  type boolean;
                  must "../bestroute-as-path-ignore = 'false' or ../load-balanc-as-path-ignore ='false'";
                  default "false";
                  description
                    "Enable/disable BGP to ignore the AS_Path attribute when selecting the optimal route. By default, BGP uses the AS_Path attribute as one of route selection rules, and a route with a shorter AS_Path is preferred. After bestroute-as-path-ignore is selected, BGP does not compare the AS_Path length.";
                }
                leaf determin-med {
                  type boolean;
                  default "false";
                  description
                    "Enable/disable deterministic MED so that the route selection result is relevant to the sequence in which routes are received.";
                }
                leaf best-external {
                  when "../../../../../../../ni:name='_public_'";
                  type boolean;
                  must "../best-external ='false' or ../determin-med ='false'";
                  default "false";
                  description
                    "Enable/disable best external route selection.";
                }
                leaf attribute-set-enable {
                  when "../../../../../../../ni:name!='_public_'";
                  type boolean;
                  default "false";
                  description
                    "Enable/disable the capability of processing attribute set.";
                }
                leaf attribute-set-mode {
                  when "../attribute-set-enable='true'";
                  type bgp:attribute-set-type;
                  default "both";
                  description
                    "The processing mode of attribute set.";
                }
                leaf add-path-select-num {
                  when "../../../../../../../ni:name='_public_'";
                  type uint8 {
                    range "2..64";
                  }
                  must "../determin-med ='false'";
                  description
                    "Number of Add-Path routes.";
                }
                leaf load-balanc-igp-metric-ignore {
                  type boolean;
                  default "false";
                  description
                    "Enable/disable BGP to ignore the IGP cost of each BGP route to the next hop when selecting routes for load balancing. By default, only the routes with the same IGP cost can participate in load balancing.";
                }
                leaf load-balanc-as-path-ignore {
                  type boolean;
                  must "../load-balanc-as-path-ignore ='false' or (../load-balanc-as-path-relax ='false' and ../bestroute-as-path-ignore ='false')";
                  default "false";
                  description
                    "Enable/disable BGP to ignore the AS_Path of each BGP route to the next hop when selecting routes for load balancing. By default, only the routes with the same AS_Path can participate in load balancing.";
                }
                leaf load-balanc-as-path-relax {
                  type boolean;
                  must "../load-balanc-as-path-relax ='false' or ../load-balanc-as-path-ignore ='false'";
                  default "false";
                  description
                    "Enable/disable BGP to ignore comparison of AS_Path attributes with the same length. By default, only the routes with the same AS_Path can participate in load balancing.";
                }
                leaf default-local-preference {
                  type uint32 {
                    range "0..4294967295";
                  }
                  default "100";
                  description
                    "The local preference of BGP routes.";
                }
                leaf default-route-import {
                  type boolean;
                  default "false";
                  description
                    "Enable/disable the function to import default routes into the BGP routing table. Default-route-imported must be used with import-routes so that default routes can be imported to the BGP routing table. If only import-routes is used, no default routes can be added to the BGP routing table. In addition, default-route-imported can only import the default routes in the routing table into the BGP routing table.";
                }
                leaf routerid-neglect {
                  type boolean;
                  default "false";
                  description
                    "Enable/disable BGP to ignore router IDs when selecting the optimal route. Comparing router IDs is the last resort in route selection. This means that if one optimal route must be selected and no other parameters can be used to break the tie, router IDs can be used. If this option is selected, the first received route will be selected as the optimal route, and BGP will ignore the router ID and peer address in route selection.";
                }
                leaf maximum-load-balancing {
                  type uint16 {
                    range "1..65535";
                  }
                  must "not (../maximum-load-balancing-ibgp>1 or ../maximum-load-balancing-ebgp>1 or ../maximum-load-balancing-eibgp) or ../maximum-load-balancing=1";
                  default "1";
                  description
                    "Specify the maximum number of equal-cost routes in the BGP routing table. The value can be 1 or an integer greater than 1. The value depends on the associated license. Equal-cost BGP routes can be generated for load balancing only when the BGP routes meet the first nine rules of the route-selection policy and have the same AS-Path attribute.";
                }
                leaf reflect-between-client {
                  type boolean;
                  default "true";
                  description
                    "Enable/disable route reflection between clients. If clients of a route reflector (RR) are fully meshed, you can disable route reflection among clients to reduce the cost.";
                }
                leaf import-rib-nexthop-invariable {
                  when "../../../../../../../ni:name!='_public_'";
                  type boolean;
                  default "false";
                  description
                    "Enable/disable the function to advertise the route without modifying the next-hop.";
                }
                leaf route-relay-tunnel {
                  when "../../../../../../../ni:name='_public_'";
                  type boolean;
                    must "not(../route-relay-tunnel='true' and /rt:routing/rt:routing-manage/rt:relay-tunnel/rt:enable='true')";
                  default "false";
                  description
                    "Enable/disable unicast route recursive-lookup tunnel.";
                }
                leaf route-relay-tunnel-selector {
                  when "../../../../../../../ni:name='_public_' and ../route-relay-tunnel='true'";
                  type leafref {
                    path "/rtp:routing-policy/rtp:tunnel-selectors/rtp:tunnel-selector/rtp:name";
                  }
                  description
                    "Unicast route tunnel selector name.";
                }
                uses bestroute-med-plus-igp-type;
                uses bestroute-router-id-prior-clusterlist-type;
                leaf bestroute-med-none-as-maximum {
                  type boolean;
                  default "false";
                  description
                    "Enable/disable BGP considers its MED as the largest MED value (4294967295). If a route does not carry MED, BGP considers its MED as the default value (0) during route selection.";
                }
                leaf ebgp-ecmp-nexthop-changed {
                  when "../maximum-load-balancing-ebgp and ../maximum-load-balancing-ebgp>1";
                  type boolean;
                  default "false";
                  description
                    "Enable/disable next hop of equal-cost EBGP routes is changed. When equal-cost EBGP routes are load-balancing traffic, the next hop of these routes is changed to a local interface before these routes are advertised. This function can be enabled only when the maximum number of equal-cost EBGP routes is greater than 1.";
                }
                leaf ibgp-ecmp-nexthop-changed {
                  when "../maximum-load-balancing-ibgp and ../maximum-load-balancing-ibgp>1";
                  type boolean;
                  default "false";
                  description
                    "Enable/disable next hop of equal-cost IBGP routes is changed. When equal-cost IBGP routes are load-balancing traffic, the next hop of these routes is changed to a local interface before these routes are advertised. This function can be enabled only when the maximum number of equal-cost IBGP routes is greater than 1.";
                }
                leaf ecmp-nexthop-changed {
                  when "../maximum-load-balancing and ../maximum-load-balancing>1";
                  type boolean;
                  default "false";
                  description
                    "Enable/disable next hop of equal-cost routes is changed. When equal-cost BGP routes are load-balancing traffic, the next hop of these routes is changed to a local interface before these routes are advertised. This function can be enabled only when the maximum number of equal-cost BGP routes is greater than 1.";
                }
                leaf maximum-load-balancing-eibgp {
                  when "../../../../../../../ni:name!='_public_'";
                  type uint16 {
                    range "1..65535";
                  }
                  must "../maximum-load-balancing-ibgp=1 and ../maximum-load-balancing-ebgp=1 and ../maximum-load-balancing=1 and ../load-balancing-eibgp-enable='false'";
                  description
                    "Specify the maximum number of equal-cost EBGP routes and IBGP routes. After the attribute is set, load balancing is performed among equal-cost BGP VPN routes, regardless of the route type, EBGP or IBGP.";
                }
                leaf eibgp-ecmp-nexthop-changed {
                  when "../maximum-load-balancing-eibgp";
                  type boolean;
                  default "false";
                  description
                    "Enable/disable next hop of equal-cost EBGP and IBGP routes is changed. When equal-cost EBGP and IBGP routes are load-balancing traffic, the next hop of these routes is changed to a local interface before these routes are advertised.";
                }
                leaf load-balancing-eibgp-enable {
                  when "../../../../../../../ni:name!='_public_'";
                  type boolean;
                  must "not (../maximum-load-balancing-ibgp>1 or ../maximum-load-balancing-ebgp>1 or ../maximum-load-balancing-eibgp) or ../load-balancing-eibgp-enable='false'";
                  default "false";
                  description
                    "Enable/disable EIBGP route load balancing.";
                }
                leaf ext-community-change {
                  type boolean;
                  default "false";
                  description
                    "Enable/disable the function to change the extended community attribute.";
                }
                leaf active-route-advertise {
                  type boolean;
                  default "false";
                  description
                    "Enable/disable the function to advertise the optimal routes in the RM module to peers.";
                }
                leaf nexthop-priority {
                  type nexthop-priority-address-type;
                  description
                    "Routes with next-hop IPv4 addresses and routes with next-hop IPv6 addresses coexist. If the next-hop address type is set to IPv4, routes with next-hop IPv4 addresses have a higher priority. If the next-hop address type is set to IPv6, routes with next-hop IPv6 addresses have a higher priority.";
                }
              }
              uses bgp-route-preference-options;
              container nexthop-recursive-lookup {
               description
                "Configure next hop iteration.";
                container common {
                description
                  "Configure next hop iteration common options.";
                  uses nexthop-recursive-lookup-restrain;                  
                  uses nexthop-recursive-lookup-default-route;
                }
                uses nexthop-recursive-lookup-delay;
              }
              container import-routes {
                description
                  "List of imported routes.";
                list import-route {
                  key "protocol process-id";
                  description
                    "Configure route import. Routes of other protocol types can be imported by BGP. By default, BGP does not import routes of other protocol types.";
                  leaf protocol {
                    type bgp:ipv4-import-route-protocol-type;
                    description
                      "Routing protocol from which routes can be imported.";
                  }
                  leaf process-id {
                    type uint32 {
                      range "0..4294967295";
                    }
                    description
                      "Process ID of an imported routing protocol. The process ID is 0, if the imported routing protocol is direct routes, static routes, UNRs, or OP-routes. The process ID must be specified range from 1 to 4294967295, if the imported routing protocol is RIP, OSPF, ISIS.";
                  }
                  choice policy-type {
                    description
                      "Set route policy or filter.";
                    case rtp-ref {
                      description
                        "Route policy.";
                      leaf policy-name {
                        type leafref {
                          path "/rtp:routing-policy/rtp:policy-definitions/rtp:policy-definition/rtp:name";
                        }
                        description
                          "When routes are imported from other routing protocols, the route-policy filter can be used to filter the routes and change route attributes.";
                      }
                    }
                  }
                }
              }
              container aggregate-routes {
                description
                  "List of summarized routes.";
                list aggregate-route {
                  key "address mask-length";
                  description
                    "Configure a summarized route in the BGP routing table. The local outbound interface of the summarized route is Null0. When another router receives the route, the route adds an outbound interface to the route. If the Origin attributes of the specific routes for the route summarization are different, the Origin attribute of the summarized route is that with the highest priority. Origin attributes are arranged in the priority order of complete > egp > igp. A summarized route carries the community attribute of each specific route.";
                  uses unicast-aggregate-routes-type;
                }
              }
              container aggregate-default-route {
                description
                  "Configure aggregate default route.";
                leaf origin-ip-prefix {
                  type leafref {
                    path "/rtp:routing-policy/rtp:ipv4-prefix-filters/rtp:ipv4-prefix-filter/rtp:name";
                 }
                  description
                   "Specify the name of an IPv4 prefix list for a summary default route. Only the name of an IPv4 prefix list can be configured in a BGP IPv4 address family.";
                }
                leaf attribute-policy {
                  when "../origin-ip-prefix";
                  type leafref {
                    path "/rtp:routing-policy/rtp:policy-definitions/rtp:policy-definition/rtp:name";
                  }
                  description
                   "Specify an attribute policy of a summary default route.";
                }
             }
              container network-routes {
                description
                  "List of network routes.";
                list network-route {
                  key "address mask-length";
                  description
                    "Configure a network route in the BGP routing table.";
                  uses network-route-ipv4;
                  leaf non-relay-tunnel {
                    when "../../../../../../../../ni:name='_public_'";
                    type boolean;
                    default "false";
                    description
                      "Enable/disable imported route relay a tunnel.";
                  }
                }
              }
              container advertise-route-to-evpns {
                when "../../../../../../ni:name!='_public_'";
                description
                  "Configure advertise route protocol.";
                uses advertise-route-to-evpn-type;
              }
              container import-ribs {
                description
                  "List of imported RIBs configuration.";
                list import-rib {
                  key "source-vpn source-address-family";
                  description
                    "Configure imported RIBs.";
                  leaf source-vpn {
                    type leafref {
                      path "/ni:network-instance/ni:instances/ni:instance/ni:name";
                    }
                    must "../../../../../../../../ni:name != current()";
                    description
                      "Source VPN name.";
                  }
                  leaf source-address-family {
                    type bgp:import-rib-ipv4-safi-type;
                    description
                      "Source address family type.";
                  }
                  leaf valid-route {
                    type boolean;
                    default "false";
                    description
                      "Enable/disable imported valid route.";
                  }
                  leaf include-label-route {
                    when "../source-address-family='ipv4uni'";
                    type boolean;
                    default "false";
                    description
                      "Enable/disable imported include label route.";
                  }
                  uses choice-policy-set {
                    refine policy-type {
                      description
                        "Specify the route-policy or filter for imported RIBs.";
                    }
                  }
                }
              }
              uses ipv4-import-filter-protocol-type;
              container export-filter-policys {
                description
                  "List of filtering policies.";
                list export-filter-policy {
                  key "protocol process-id";
                  description
                    "Apply a filtering policy. It is used to filter the routes to be advertised to the peer. By default, routes are not filtered.";
                  leaf protocol {
                    type bgp:ipv4-export-filter-protocol-type;
                    description
                      "Specify the name of a routing protocol. The routing protocol takes effect only on the routes to be advertised. The IPv4 address family supports the direct, IS-IS, OSPF, RIP, and static routing protocols. The IPv6 unicast address family of a public network instance supports the direct, IS-IS, OSPFv3, RIPng, and static routing protocols. The IPv6 address family of a VPNv6 instance supports the direct, IS-IS, RIPng, and static routing protocols.";
                  }
                  leaf process-id {
                    type uint32 {
                    range "0..4294967295";
                    }
                    description
                      "Specify the process ID required to be matched. The value is an integer ranging from 0 to 4294967295. If direct or static routes need to be filtered, no process ID is required.";
                  }
                  uses ipv4-filter-protocol-policy-choice-type;
                }
              }
              container lsp-options {
                when "../../../../../../ni:name='_public_'";
                description
                  "Configure parameters for lsp.";
                uses safi-lsp-options;
              }
              container segment-routing-ipv6 {
                description
                  "Configure BGP segment-routing IPv6.";
                leaf srv6-best-effort-enable {
                  type empty;
                  description
                    "Enable SRv6 BE iteration.";
                }
                leaf srv6-traffic-engineer-enable {
                when "../../../../../../../ni:name!='_public_'";				
                  type empty;
                  description
                    "Enable SRv6 TE iteration.";
                }
              }
              uses vrf-af-dampening-routes;
              uses bgp:slow-peer-type;
              uses routing-table-rib-only-type {
                refine routing-table-rib-only/enable {
                  must "not (../../common/active-route-advertise = 'true' and ../enable = 'true')";
                }
              }
            }
            container ipv6-unicast {
              when "../type = 'ipv6uni'";
              description
                "Configure IPv6 unicast options.";
              container common {
                description
                  "Configure IPv6 unicast common options.";
                leaf auto-frr {
                  type boolean;
                  default "false";
                  description
                    "Enable/disable BGP auto FRR. If IP FRR, VPN FRR, and Auto FRR are all enabled, IP FRR and VPN FRR take precedence over Auto FRR. If a route fails to match the routing policy of IP FRR or VPN FRR, Auto FRR takes effect.";
                }
                leaf route-select-delay {
                  type uint16 {
                    range "0..3600";
                  }
                  units "s";
                  default "0";
                  description
                    "Route selection delay.";
                }
                uses reflector-cluster-type;
                uses reflect-type;
                leaf maximum-load-balancing-ibgp {
                  type uint16 {
                    range "1..65535";
                  }
                  default "1";
                  description
                    "Specify the maximum number of equal-cost IBGP routes.";
                }
                leaf maximum-load-balancing-ebgp {
                  type uint16 {
                    range "1..65535";
                  }
                  default "1";
                  description
                    "Specify the maximum number of equal-cost EBGP routes.";
                }
                leaf explicit-null {
                  when "../../../../../../../ni:name='_public_'";
                  type boolean;
                  must "not(../lsp-operation='pop-go' and ../explicit-null='true')";
                  default "false";
                  description
                    "Enable/disable the function to explicit null. After 6PE routes are enabled to share a single label, all routes share the explicit-null label 2 when the 6PE sends IPv6 routes to its 6PE peer. This can save label resources on the 6PE. Therefore, when there are a large number of IPv6 routes that need to be sent, the problem that the IPv6 routes cannot be forwarded due to the shortage of labels can be avoided.";
                }
                leaf lsp-operation {
                  when "../../../../../../../ni:name='_public_'";
                  type lsp-operation-type;
                  must "not(../lsp-operation='pop-go' and ../explicit-null='true')";
                  default "pop";
                  description
                    "Label operation mode.";
                }
                leaf nexthop-select-depend-type {
                  when "../../../../../../../ni:name='_public_'";
                  type select-depend-type;
                  default "depend-tunnel";
                  description
                    "Specify the route iteration mode: IP or tunnel. In tunnel mode, the labeled BGP IPv4 route can participate in route selection only after its next hop is iterated to an LSP. In IP 
                    mode, the labeled BGP IPv4 route can participate in route selection only after its next hop is iterated to an IP address. By default, the labeled BGP IPv4 route can participate in route selection 
                    if its next hop can be iterated to an IP address, regardless of whether the LSP of the next hop exists. This allows the RR that is not enabled with MPLS to forward labeled routes. In non-RR 
                    networking or RR networking where the BGP next hop is changed, BGP needs to check whether there is an LSP destined for the next hop. If such an LSP is not found, BGP needs to establish an LSP in 
                    advance. If the default setting is adopted, a labeled BGP IPv4 unicast route may be selected prior to LSP establishment. As a result, services are incorrectly switched before LSP establishment and 
                    service stability is affected. Therefore, allow route selection only after the labeled BGP IPv4 route is iterated to an LSP.";
                }
                leaf nexthop-inherit-ip-cost {
                  when "../nexthop-select-depend-type='depend-tunnel'";
                  type boolean;
                  default "false";
                  description
                    "Enable/disable next hop iteration mode to IP. Specify the route iteration mode: IP or tunnel. In tunnel mode, the labeled BGP IPv4 route can participate in route selection only after its next hop is iterated to an LSP.";
                }
                leaf nexthop-resolve-aigp {
                  when "../../../../../../../ni:name!='_public_'";
                  type boolean;
                  default "false";
                  description
                    "Enable/disable route with AIGP attribute for route selection.";
                }
                leaf always-compare-med {
                  type boolean;
                  default "false";
                  description
                    "Enable/disable BGP to compare the MEDs of routes from peers in different ASs in route selection. If 
                    there are multiple reachable routes to the same destination, the route with the smallest MED is preferred. Do not use this option unless different ASs use the same IGP and route selection mode.";
                }
                leaf default-med {
                  type uint32;
                  default "0";
                  description
                    "Specify the Multi-Exit-Discriminator (MED) of BGP routes. The value is an integer. This value is valid only for the imported routes and BGP summarized routes on the local router.";
                }
                leaf nexthop-third-party {
                  type boolean;
                  default "false";
                  description
                    "Enable/disable BGP third-party next hop.";
                }
                leaf supernet-unicast-advertise {
                  type boolean;
                  default "false";
                  description
                    "Enable/disable advertise supernet unicast routes.";
                }
                leaf bestroute-med-confederation {
                  when "../../../../../../../ni:name='_public_'";
                  type boolean;
                  default "false";
                  description
                    "Enable/disable BGP to compare Med value only within the federation.";
                }
                leaf bestroute-as-path-ignore {
                  type boolean;
                  must "../bestroute-as-path-ignore = 'false' or ../load-balanc-as-path-ignore ='false'";
                  default "false";
                  description
                    "Enable/disable BGP to ignore the AS_Path attribute when selecting the optimal route. By default, BGP uses the AS_Path attribute as one of route selection rules, and a route with a shorter AS_Path is preferred. After bestroute-as-path-ignore is selected, BGP does not compare the AS_Path length.";
                }
                leaf determin-med {
                  type boolean;
                  default "false";
                  description
                    "Enable/disable deterministic MED so that the route selection result is relevant to the sequence in which routes are received.";
                }
                leaf best-external {
                  when "../../../../../../../ni:name='_public_'";
                  type boolean;
                  must "../best-external ='false' or ../determin-med ='false'";
                  default "false";
                  description
                    "Enable/disable best external route selection.";
                }
                leaf attribute-set-enable {
                  when "../../../../../../../ni:name!='_public_'";
                  type boolean;
                  default "false";
                  description
                    "Enable/disable the capability of processing attribute set.";
                }
                leaf attribute-set-mode {
                  when "../attribute-set-enable='true'";
                  type bgp:attribute-set-type;
                  default "both";
                  description
                    "The processing mode of attribute set.";
                }
                leaf add-path-select-num {
                  when "../../../../../../../ni:name='_public_'";
                  type uint8 {
                    range "2..64";
                  }
                  must "../determin-med ='false'";
                  description
                    "Number of add-path routes.";
                }
                leaf load-balanc-igp-metric-ignore {
                  type boolean;
                  default "false";
                  description
                    "Enable/disable BGP to ignore the IGP cost of each BGP route to the next hop when selecting routes for load balancing. By default, only the routes with the same IGP cost can participate in load balancing.";
                }
                leaf load-balanc-as-path-ignore {
                  type boolean;
                  must "../load-balanc-as-path-ignore ='false' or (../load-balanc-as-path-relax ='false' and ../bestroute-as-path-ignore ='false')";
                  default "false";
                  description
                    "Enable/disable BGP to ignore the AS_Path of each BGP route to the next hop when selecting routes for load balancing. By default, only the routes with the same AS_Path can participate in load balancing.";
                }
                leaf load-balanc-as-path-relax {
                  type boolean;
                  must "../load-balanc-as-path-relax ='false' or ../load-balanc-as-path-ignore ='false'";
                  default "false";
                  description
                    "Enable/disable BGP to ignore comparison of AS_Path attributes with the same length. By default, only the routes with the same AS_Path can participate in load balancing.";
                }
                leaf default-local-preference {
                  type uint32 {
                    range "0..4294967295";
                  }
                  default "100";
                  description
                    "The local preference of BGP routes.";
                }
                leaf default-route-import {
                  type boolean;
                  default "false";
                  description
                    "Enable/disable the function to import default routes into the BGP routing table. default-route-imported must be used with import-routes so that default routes can be imported to the BGP routing table. If only import-routes is used, no default routes can be added to the BGP routing table. In addition, default-route-imported can only import the default routes in the routing table into the BGP routing table.";
                }
                leaf routerid-neglect {
                  type boolean;
                  default "false";
                  description
                    "Enable/disable BGP to ignore router IDs when selecting the optimal route. Comparing router IDs is the last resort in route selection. This means that if one optimal route must be selected and no other parameters can be used to break the tie, router IDs can be used. If this option is selected, the first received route will be selected as the optimal route, and BGP will ignore the router ID and peer address in route selection.";
                }
                leaf maximum-load-balancing {
                  type uint16 {
                    range "1..65535";
                  }
                  default "1";
                  description
                    "Specify the maximum number of equal-cost routes in the BGP routing table. The value depends on the associated license. Equal-cost BGP routes can be generated for load balancing only when the BGP routes meet the first nine rules of the route-selection policy and have the same AS-Path attribute.";
                }
                leaf reflect-between-client {
                  type boolean;
                  default "true";
                  description
                    "Enable/disable route reflection between clients. If clients of a route reflector (RR) are fully meshed, you can disable route reflection among clients to reduce the cost.";
                }
                leaf best-route-bit-error-detection {
                  when "../../../../../../../ni:name!='_public_'";
                  type boolean;
                  default "false";
                  description
                    "Enable/disable the function to reroute traffic when a bit error event occurs.";
                }
                leaf import-rib-nexthop-invariable {
                  when "../../../../../../../ni:name!='_public_'";
                  type boolean;
                  default "false";
                  description
                    "Enable/disable advertise the route without modifying the next-hop.";
                }
                leaf route-relay-tunnel-v4 {
                  type boolean;
                  default "false";
                  description
                    "Enable/disable unicast-route recursive-lookup tunnel.";
                }
                leaf route-relay-tunnel-v4-selector {
                  when "../route-relay-tunnel-v4='true'";
                  type leafref {
                    path "/rtp:routing-policy/rtp:tunnel-selectors/rtp:tunnel-selector/rtp:name";
                  }
                  description
                    "Unicast route tunnel selector name.";
                }
                uses bestroute-med-plus-igp-type;
                uses bestroute-router-id-prior-clusterlist-type;
                leaf bestroute-med-none-as-maximum {
                  type boolean;
                  default "false";
                  description
                    "Enable/disable BGP considers its MED as the largest MED value (4294967295). If a route does not carry MED, BGP considers its MED as the default value (0) during route selection.";
                }
                leaf nexthop-priority {
                  when "../../../../../../../ni:name!='_public_'";
                  type nexthop-priority-address-type;
                  description
                    "In the VRF instance, routes with next-hop IPv4 addresses and routes with next-hop IPv6 addresses coexist. If the next-hop address type is set to IPv4, routes with next-hop IPv4 addresses have a higher priority. If the next-hop address type is set to IPv6, routes with next-hop IPv6 addresses have a higher priority.";
                }
                leaf ebgp-ecmp-nexthop-changed {
                  when "../maximum-load-balancing-ebgp and ../maximum-load-balancing-ebgp>1";
                  type boolean;
                  default "false";
                  description
                    "Enable/disable next hop of equal-cost EBGP routes is changed. Enable/disable next hop of equal-cost EBGP routes is changed. When equal-cost EBGP routes are load-balancing traffic, the next hop of these routes is changed to a local interface before these routes are advertised. This function can be enabled only when the maximum number of equal-cost EBGP routes is greater than 1.";
                }
                leaf ibgp-ecmp-nexthop-changed {
                  when "../maximum-load-balancing-ibgp and ../maximum-load-balancing-ibgp>1";
                  type boolean;
                  default "false";
                  description
                    "Enable/disable next hop of equal-cost IBGP routes is changed. When equal-cost IBGP routes are load-balancing traffic, the next hop of these routes is changed to a local interface before these routes are advertised. This function can be enabled only when the maximum number of equal-cost IBGP routes is greater than 1.";
                }
                leaf ecmp-nexthop-changed {
                  when "../maximum-load-balancing and ../maximum-load-balancing>1";
                  type boolean;
                  default "false";
                  description
                    "Enable/disable next hop of equal-cost routes is changed. When equal-cost BGP routes are load-balancing traffic, the next hop of these routes is changed to a local interface before these routes are advertised. This function can be enabled only when the maximum number of equal-cost BGP routes is greater than 1.";
                }
                leaf maximum-load-balancing-eibgp {
                  when "../../../../../../../ni:name!='_public_'";
                  type uint16 {
                    range "1..65535";
                  }
                  must "../maximum-load-balancing-ibgp=1 and ../maximum-load-balancing-ebgp=1 and ../maximum-load-balancing=1 and ../load-balancing-eibgp-enable='false'";
                  description
                    "Specify the maximum number of equal-cost EBGP routes and IBGP routes. After the attribute is set, load balancing is performed among equal-cost BGP VPN routes, regardless of the route type, EBGP or IBGP.";
                }
                leaf eibgp-ecmp-nexthop-changed {
                  when "../maximum-load-balancing-eibgp";
                  type boolean;
                  default "false";
                  description
                    "Enable/disable next hop of equal-cost EBGP and IBGP routes is changed. When equal-cost EBGP and IBGP routes are load-balancing traffic, the next hop of these routes is changed to a local interface before these routes are advertised.";
                }
                leaf load-balancing-eibgp-enable {
                  when "../../../../../../../ni:name!='_public_'";
                  type boolean;
                  must "not (../maximum-load-balancing-ibgp>1 or ../maximum-load-balancing-ebgp>1 or ../maximum-load-balancing-eibgp) or ../load-balancing-eibgp-enable='false'";
                  default "false";
                  description
                    "Enable/disable EIBGP route load balancing.";
                }
                leaf ext-community-change {
                  type boolean;
                  default "false";
                  description
                    "Enable/disable the function to change the extended community attribute.";
                }
                leaf active-route-advertise {
                  type boolean;
                  default "false";
                  description
                    "Enable/disable the function to advertise the optimal routes in the RM module to peers.";
                }
              }
              uses bgp-route-preference-options;
              container nexthop-recursive-lookup {
               description
                "Configure next hop iteration.";
                container common {
                  description
                    "Configure next hop iteration common options.";
                  uses nexthop-recursive-lookup-restrain;
                  uses nexthop-recursive-lookup-default-route;
                }
                uses nexthop-recursive-lookup-delay;
              }
              container import-routes {
                description
                  "List of imported routes.";
                list import-route {
                  key "protocol process-id";
                  description
                    "Configure route import. Routes of other protocol types can be imported by BGP. By default, BGP does not import routes of other protocol types.";
                  leaf protocol {
                    type bgp:ipv6-import-route-protocol-type;
                    description
                      "Routing protocol from which routes can be imported.";
                  }
                  leaf process-id {
                    type uint32 {
                      range "0..4294967295";
                    }
                    description
                      "Process ID of an imported routing protocol. The process ID is 0, if the imported routing protocol is direct routes, static routes, UNRs, or OP-routes. The process ID must be specified range from 1 to 4294967295, if the imported routing protocol is ISIS, RIPng, or OSPFv3.";
                  }
                  choice policy-type {
                    description
                      "Set route policy or filter.";
                    case rtp-ref {
                      description
                        "Route policy.";
                      leaf policy-name {
                        type leafref {
                          path "/rtp:routing-policy/rtp:policy-definitions/rtp:policy-definition/rtp:name";
                        }
                        description
                          "When routes are imported from other routing protocols, the route-policy filter can be used to filter the routes and change route attributes.";
                      }
                    }
                  }
                }
              }
              container aggregate-routes {
                description
                  "List of summarized routes.";
                list aggregate-route {
                  key "address mask-length";
                  description
                    "Configure a summarized route in the BGP routing table. The local outbound interface of the summarized route is Null0. When another router receives the route, the route adds an outbound interface to the route. By default, route summarization is not performed. If the Origin attributes of the specific routes for the route summarization are different, the Origin attribute of the summarized route is that with the highest priority. Origin attributes are arranged in the priority order of complete > egp > igp. A summarized route carries the community attribute of each specific route.";
                  uses unicast-aggregate-routes-type;
                }
              }
              container aggregate-default-route {
                description
                  "Configure aggregate default route.";
                leaf origin-ipv6-prefix {
                  type leafref {
                    path "/rtp:routing-policy/rtp:ipv6-prefix-filters/rtp:ipv6-prefix-filter/rtp:name";
                  }
                  description
                   "Specify the name of an IPv6 prefix list for a summary default route. Only the name of an IPv6 prefix list can be configured in a BGP IPv6 address family.";
                }
                leaf attribute-policy {
                  when "../origin-ipv6-prefix";
                  type leafref {
                    path "/rtp:routing-policy/rtp:policy-definitions/rtp:policy-definition/rtp:name";
                  }
                  description
                   "Specify an attribute policy of a summary default route.";
                }
             }
              container network-routes {
                description
                  "List of network routes.";
                list network-route {
                  key "address mask-length";
                  description
                    "Configure a network route in the BGP routing table.";
                  uses network-route-ipv6;
                }
              }
              container advertise-route-to-evpns {
                when "../../../../../../ni:name!='_public_'";
                description
                  "Configure advertise route protocol.";
                uses advertise-route-to-evpn-type;
              }
              container import-ribs {
                description
                  "List of imported RIBs configuration.";
                list import-rib {
                  key "source-vpn source-address-family";
                  description
                    "Configure imported RIBs.";
                  leaf source-vpn {
                    type leafref {
                      path "/ni:network-instance/ni:instances/ni:instance/ni:name";
                    }
                    must "../../../../../../../../ni:name != current()";
                    description
                      "Source VPN name for imported RIBs.";
                  }
                  leaf source-address-family {
                    type bgp:import-rib-ipv6-safi-type;
                    description
                      "Source address family type for imported RIBs.";
                  }
                  leaf valid-route {
                    type boolean;
                    default "false";
                    description
                      "Enable/disable imported valid route.";
                  }
                  leaf include-label-route {
                    type boolean;
                    default "false";
                    description
                      "Enable/disable imported include label route.";
                  }
                  uses choice-policy-set {
                    refine policy-type {
                    description
                      "Specify the route-policy or filter for imported RIBs.";
                    }
                  }
                }
              }
              container segment-routing-ipv6 {
                when "../../../../../../ni:name='_public_'";
                description
                  "Configure BGP segment-routing IPv6.";
                leaf srv6-best-effort-enable {
                  type empty;
                  description
                    "Enable SRv6 BE iteration.";
                }
              }
              uses vrf-af-dampening-routes;
              uses ipv6-import-filter-protocol-type;
              uses ipv6-export-filter-protocol-type;
              uses bgp:slow-peer-type;
              uses routing-table-rib-only-type {
                refine routing-table-rib-only/enable {
                  must "not (../../common/active-route-advertise = 'true' and ../enable = 'true')";
                }
              }
            }
            container ipv4-vpn {
              when "../type = 'ipv4vpn'";
              description
                "Configure IPv4 VPNv4 options.";
              uses vpn-target-type;
              uses reflector-cluster-type;
              uses reflect-type;
              leaf auto-frr {
                type boolean;
                default "false";
                description
                  "Enable/disable BGP Auto FRR. If IP FRR, VPN FRR, and Auto FRR are all enabled, IP FRR and VPN FRR take precedence over Auto FRR. If a route fails to match the routing policy of IP FRR or VPN FRR, Auto FRR takes effect.";
              }
              leaf tunnel-selector-name {
                type leafref {
                  path "/rtp:routing-policy/rtp:tunnel-selectors/rtp:tunnel-selector/rtp:name";
                }
                description
                  "Configure a tunnel selector and apply it to the BGP IPv4 unicast, BGP VPNv4 address families and BGP VPNv6 address families so that IPv4,VPNv4 and VPNv6 labeled routes can be iterated to tunnels based on the tunnel selector.";
              }
              leaf route-select-delay {
                type uint16 {
                  range "0..3600";
                }
                units "s";
                default "0";
                description
                  "Route selection delay.";
              }
              leaf apply-label-mode {
                type apply-label-type;
                default "per-route";
                description
                  "Method of distributing labels to VPNV4 and VPNV6 routes. The way which assigns the label depends on the paf value. If there are a large number of routes, assign a label for the routes that have same nexthop and out-label. This allows all routes which have same nexthop and out-label to use one label.";
              }
              leaf nexthop-select-depend-type {
                type select-depend-type;
                default "depend-ip";
                description
                  "Specify the route iteration mode: IP or tunnel. In tunnel mode, the labeled BGP IPv4 route can participate in route selection only after its next hop is iterated to an LSP. In IP 
                  mode, the labeled BGP IPv4 route can participate in route selection only after its next hop is iterated to an IP address. By default, the labeled BGP IPv4 route can participate in route selection 
                  if its next hop can be iterated to an IP address, regardless of whether the LSP of the next hop exists. This allows the RR that is not enabled with MPLS to forward labeled routes. In non-RR 
                  networking or RR networking where the BGP next hop is changed, BGP needs to check whether there is an LSP destined for the next hop. If such an LSP is not found, BGP needs to establish an LSP in 
                  advance. If the default setting is adopted, a labeled BGP IPv4 unicast route may be selected prior to LSP establishment. As a result, services are incorrectly switched before LSP establishment and 
                  service stability is affected. Therefore, allow route selection only after the labeled BGP IPv4 route is iterated to an LSP.";
              }
              leaf default-med {
                type uint32;
                default "0";
                description
                  "Specify the Multi-Exit-Discriminator (MED) of BGP routes. The value is an integer. This value is valid only for the imported routes and BGP summarized routes on the local router.";
              }
              leaf best-external {
                when "../../../../../../ni:name='_public_'";
                type boolean;
                default "false";
                description
                  "Enable/disable best external route selection.";
              }
              leaf label-free-delay {
                type uint8 {
                  range "0..180";
                }
                units "s";
                default "0";
                description
                  "Label free delay.";
              }
              leaf add-path-select-num {
                when "../../../../../../ni:name='_public_'";
                type uint8 {
                  range "2..64";
                }
                description
                  "Number of Add-Path routes.";
              }
              leaf default-local-preference {
                type uint32 {
                  range "0..4294967295";
                }
                default "100";
                description
                  "The local preference of BGP routes.";
              }
              uses bestroute-med-plus-igp-type;
              uses bestroute-router-id-prior-clusterlist-type;
              leaf reflect-between-client {
                type boolean;
                default "true";
                description
                  "Enable/disable route reflection between clients. If clients of a route reflector (RR) are fully meshed, you can disable route reflection among clients to reduce the cost.";
              }
              uses vrf-af-dampening-routes-ext;
              container nexthop-recursive-lookup {
               description
                "Configure next hop iteration.";
                container common {
                  description
                    "Configure next hop iteration common options.";
                  uses nexthop-recursive-lookup-restrain;
                  uses nexthop-recursive-lookup-default-route;
                  }
                  uses nexthop-recursive-lookup-delay;          
                  uses bit-error-detection-type;
              }
              uses ipv4-import-filter-protocol-type;
              uses ipv4vpn-export-filter-protocol-type;
              uses bgp:slow-peer-type;
            }
            container ipv6-vpn {
              when "../type = 'ipv6vpn'";
              description
                "Configure IPv6 VPNv6 options.";
              uses vpn-target-type;
              uses reflector-cluster-type;
              uses reflect-type;
              leaf auto-frr {
                type boolean;
                default "false";
                description
                  "Enable/disable BGP Auto FRR. If IP FRR, VPN FRR, and Auto FRR are all enabled, IP FRR and VPN FRR take precedence over Auto FRR. If a route fails to match the routing policy of IP FRR or VPN FRR, Auto FRR takes effect.";
              }
              leaf tunnel-selector-name {
                type leafref {
                  path "/rtp:routing-policy/rtp:tunnel-selectors/rtp:tunnel-selector/rtp:name";
                }
                description
                  "Configure a tunnel selector and apply it to the BGP IPv4 unicast, BGP VPNv4 address families and BGP VPNv6 address families so that IPv4,VPNv4 and VPNv6 labeled routes can be iterated to tunnels based on the tunnel selector. By default, no tunnel selector is configured.";
              }
              leaf route-select-delay {
                type uint16 {
                  range "0..3600";
                }
                units "s";
                default "0";
                description
                  "Route selection delay.";
              }
              leaf apply-label-mode {
                type apply-label-type;
                default "per-route";
                description
                  "Method of distributing labels to VPNV4 and VPNV6 routes. The way which assigns the label depends on the paf value. If there are a large number of routes, assign a label for the routes that have same nexthop and out-label. This allows all routes which have same nexthop and out-label to use one label.";
              }
              leaf nexthop-select-depend-type {
                type select-depend-type;
                default "depend-ip";
                description
                  "Specify the route iteration mode: IP or tunnel. In tunnel mode, the labeled BGP IPv4 route can participate in route selection only after its next hop is iterated to an LSP. In IP 
                  mode, the labeled BGP IPv4 route can participate in route selection only after its next hop is iterated to an IP address. By default, the labeled BGP IPv4 route can participate in route selection 
                  if its next hop can be iterated to an IP address, regardless of whether the LSP of the next hop exists. This allows the RR that is not enabled with MPLS to forward labeled routes. In non-RR 
                  networking or RR networking where the BGP next hop is changed, BGP needs to check whether there is an LSP destined for the next hop. If such an LSP is not found, BGP needs to establish an LSP in 
                  advance. If the default setting is adopted, a labeled BGP IPv4 unicast route may be selected prior to LSP establishment. As a result, services are incorrectly switched before LSP establishment and 
                  service stability is affected. Therefore, allow route selection only after the labeled BGP IPv4 route is iterated to an LSP.";
              }
              leaf default-med {
                type uint32;
                default "0";
                description
                  "Specify the Multi-Exit-Discriminator (MED) of BGP routes. The value is an integer. This value is valid only for the imported routes and BGP summarized routes on the local router.";
              }
              leaf best-external {
                when "../../../../../../ni:name='_public_'";
                type boolean;
                default "false";
                description
                  "Enable/disable best external route selection.";
              }
              leaf add-path-select-num {
                when "../../../../../../ni:name='_public_'";
                type uint8 {
                  range "2..64";
                }
                description
                  "Number of add-path routes.";
              }
              leaf default-local-preference {
                type uint32 {
                  range "0..4294967295";
                }
                default "100";
                description
                  "The local preference of BGP routes.";
              }
              uses bestroute-med-plus-igp-type;
              uses bestroute-router-id-prior-clusterlist-type;
              leaf reflect-between-client {
                type boolean;
                default "true";
                description
                  "Enable/disable route reflection between clients. If clients of a route reflector (RR) are fully meshed, you can disable route reflection among clients to reduce the cost.";
              }
              leaf label-free-delay {
                type uint8 {
                  range "0..180";
                }
                units "s";
                default "0";
                description
                  "Label free delay.";
              }
              container nexthop-recursive-lookup {
               description
                "Configure next hop iteration.";
                  container common {
                  description
                    "Configure next hop iteration common options.";
                    uses nexthop-recursive-lookup-restrain;
                    uses nexthop-recursive-lookup-default-route;
                  }
                  uses nexthop-recursive-lookup-delay;
                  uses bit-error-detection-type;
              }
              uses ipv6-import-filter-protocol-type;
              uses ipv6vpn-export-filter-protocol-type;
              uses bgp:slow-peer-type;
            }
            container ipv4-labeluni {
              when "../type = 'ipv4labeluni'";
              description
                "Configure IPv4 label unicast options.";
              container common {
                description
                  "Configure IPv4 label unicast common options.";
                leaf auto-frr {
                  type boolean;
                  default "false";
                  description
                    "Enable/disable BGP Auto FRR. If IP FRR, VPN FRR, and Auto FRR are all enabled, IP FRR and VPN FRR take precedence over Auto FRR. If a route fails to match the routing policy of IP FRR or VPN FRR, Auto FRR takes effect.";
                }
                leaf tunnel-selector-name {
                  when "../../../../../../../ni:name='_public_'";
                  type leafref {
                    path "/rtp:routing-policy/rtp:tunnel-selectors/rtp:tunnel-selector/rtp:name";
                  }
                  description
                    "Configure a tunnel selector and apply it to the BGP IPv4 unicast, BGP VPNv4 address families and BGP VPNv6 address families so that IPv4,VPNv4 and VPNv6 labeled routes can be iterated to tunnels based on the tunnel selector. By default, no tunnel selector is configured.";
                }
                leaf tunnel-selector-all {
                  when "../tunnel-selector-name";
                  type boolean;
                  default "false";
                  description
                    "Enable/disable tunnel selector for labeled, imported, and network segment routes.";
                }
                leaf nexthop-select-depend-type {
                  when "../../../../../../../ni:name='_public_'";
                  type select-depend-type;
                  default "depend-tunnel";
                  description
                    "Specify the route iteration mode: IP or tunnel. In tunnel mode, the labeled BGP IPv4 route can participate in route selection only after its next hop is iterated to an LSP. In IP 
                    mode, the labeled BGP IPv4 route can participate in route selection only after its next hop is iterated to an IP address. By default, the labeled BGP IPv4 route can participate in route selection 
                    if its next hop can be iterated to an IP address, regardless of whether the LSP of the next hop exists. This allows the RR that is not enabled with MPLS to forward labeled routes. In non-RR 
                    networking or RR networking where the BGP next hop is changed, BGP needs to check whether there is an LSP destined for the next hop. If such an LSP is not found, BGP needs to establish an LSP in 
                    advance. If the default setting is adopted, a labeled BGP IPv4 unicast route may be selected prior to LSP establishment. As a result, services are incorrectly switched before LSP establishment and 
                    service stability is affected. Therefore, allow route selection only after the labeled BGP IPv4 route is iterated to an LSP.";
                }
                leaf nexthop-inherit-ip-cost {
                  when "../nexthop-select-depend-type='depend-tunnel'";
                  type boolean;
                  default "false";
                  description
                    "Enable/disable next hop iteration mode to IP. Specify the route iteration mode: IP or tunnel. In tunnel mode, the labeled BGP IPv4 route can participate in route selection only after its next hop is iterated to an LSP.";
                }
                leaf always-compare-med {
                  type boolean;
                  default "false";
                  description
                    "Enable/disable BGP to compare the MEDs of routes from peers in different ASs in route selection. If 
                    there are multiple reachable routes to the same destination, the route with the smallest MED is preferred. Do not use this option unless different ASs use the same IGP and route selection mode.";
                }
                leaf default-med {
                  type uint32;
                  default "0";
                  description
                    "Specify the Multi-Exit-Discriminator (MED) of BGP routes. The value is an integer. This value is valid only for the imported routes and BGP summarized routes on the local router.";
                }
                leaf best-route-bit-error-detection {
                  when "../../../../../../../ni:name!='_public_'";
                  type boolean;
                  default "false";
                  description
                    "Enable/disable the function to reroute traffic when a bit error event occurs.";
                }
                leaf supernet-label-advertise {
                  type boolean;
                  default "true";
                  description
                    "Enable/disable the function to advertise supernet labeled routes.";
                }
                leaf lsp-mtu {
                  when "../../../../../../../ni:name='_public_'";
                  type uint16 {
                    range "46..65535";
                  }
                  default "1500";
                  description
                    "BGP LSP MTU.";
                }
                leaf label-free-delay {
                  type uint8 {
                    range "0..180";
                  }
                  units "s";
                  default "0";
                  description
                    "Label free delay.";
                }
                leaf bestroute-med-confederation {
                  when "../../../../../../../ni:name='_public_'";
                  type boolean;
                  default "false";
                  description
                    "Enable/disable BGP to compare Med value only within the federation.";
                }
                leaf bestroute-as-path-ignore {
                  type boolean;
                  must "../bestroute-as-path-ignore = 'false' or ../load-balanc-as-path-ignore ='false'";
                  default "false";
                  description
                    "Enable/disable BGP to ignore the AS_Path attribute when selecting the optimal route. By default, BGP uses the AS_Path attribute as one of route selection rules, and a route with a shorter AS_Path is preferred. After bestroute-as-path-ignore is selected, BGP does not compare the AS_Path length.";
                }
                leaf determin-med {
                  type boolean;
                  must "../determin-med ='false' or (not(../add-path-select-num) and ../best-external ='false')";
                  default "false";
                  description
                    "Enable/disable deterministic MED so that the route selection result is relevant to the sequence in which routes are received.";
                }
                leaf best-external {
                  when "../../../../../../../ni:name='_public_'";
                  type boolean;
                  must "../best-external ='false' or ../determin-med ='false'";
                  default "false";
                  description
                    "Enable/disable best external route selection.";
                }
                leaf add-path-select-num {
                  when "../../../../../../../ni:name='_public_'";
                  type uint8 {
                    range "2..64";
                  }
                  must "../determin-med ='false'";
                  description
                    "Number of add-path routes.";
                }
                leaf load-balanc-igp-metric-ignore {
                  when "../../../../../../../ni:name='_public_'";
                  type boolean;
                  default "false";
                  description
                    "Enable/disable BGP to ignore the IGP cost of each BGP route to the next hop when selecting routes for load balancing. By default, only the routes with the same IGP cost can participate in load balancing.";
                }
                leaf load-balanc-as-path-ignore {
                  when "../../../../../../../ni:name='_public_'";
                  type boolean;
                  must "../load-balanc-as-path-ignore ='false' or (../load-balanc-as-path-relax ='false' and ../bestroute-as-path-ignore ='false')";
                  default "false";
                  description
                    "Enable/disable BGP to ignore the AS_Path of each BGP route to the next hop when selecting routes for load balancing. By default, only the routes with the same AS_Path can participate in load balancing.";
                }
                leaf load-balanc-as-path-relax {
                  when "../../../../../../../ni:name='_public_'";
                  type boolean;
                  must "../load-balanc-as-path-relax ='false' or ../load-balanc-as-path-ignore ='false'";
                  default "false";
                  description
                    "Enable/disable BGP to ignore comparison of AS_Path attributes with the same length. By default, only the routes with the same AS_Path can participate in load balancing.";
                }
                leaf default-local-preference {
                  type uint32 {
                    range "0..4294967295";
                  }
                  default "100";
                  description
                    "The local preference of BGP routes.";
                }
                leaf default-route-import {
                  type boolean;
                  default "false";
                  description
                    "Enable/disable the function to import default routes into the BGP routing table. default-route-imported must be used with import-routes so that default routes can be imported to the BGP routing table. If only import-routes is used, no default routes can be added to the BGP routing table. In addition, default-route-imported can only import the default routes in the routing table into the BGP routing table.";
                }
                leaf routerid-neglect {
                  type boolean;
                  default "false";
                  description
                    "Enable/disable BGP to ignore router IDs when selecting the optimal route. Comparing router IDs is the last resort in route selection. This means that if one optimal route must be selected and no other parameters can be used to break the tie, router IDs can be used. If this option is selected, the first received route will be selected as the optimal route, and BGP will ignore the router ID and peer address in route selection.";
                }
                leaf route-select-delay {
                  type uint16 {
                    range "0..3600";
                  }
                  units "s";
                  default "0";
                  description
                    "Route selection delay.";
                }
                leaf import-rib-nexthop-invariable {
                  when "../../../../../../../ni:name!='_public_'";
                  type boolean;
                  default "false";
                  description
                    "Enable/disable the command to enable advertise the route without modifying the next-hop.";
                }
                uses reflect-type;
                uses reflector-cluster-type;
                leaf reflect-between-client {
                  type boolean;
                  default "true";
                  description
                    "Enable/disable route reflection between clients. If clients of a route reflector (RR) are fully meshed, you can disable route reflection among clients to reduce the cost.";
                }
                uses bestroute-med-plus-igp-type;
                uses bestroute-router-id-prior-clusterlist-type;
                leaf bestroute-med-none-as-maximum {
                  type boolean;
                  default "false";
                  description
                    "Enable/disable BGP considers its MED as the largest MED value (4294967295). If a route does not carry MED, BGP considers its MED as the default value (0) during route selection.";
                }
                leaf ext-community-change {
                  type boolean;
                  default "false";
                  description
                    "Enable/disable the function to change the extended community attribute.";
                }
              }
              container nexthop-recursive-lookup {
               description
                "Configure next hop iteration.";
                container common {
                  description
                    "Configure next hop iteration common options.";
                    uses nexthop-recursive-lookup-restrain;
                }
              }
              uses import-routes-type;
              container network-routes {
                description
                  "List of network routes.";
                list network-route {
                  key "address mask-length";
                  description
                    "Configure a network route in the BGP routing table.";
                  uses network-route-ipv4;
                  leaf non-relay-tunnel {
                    when "../../../../../../../../ni:name='_public_'";
                    type boolean;
                    default "false";
                    description
                      "Enable/disable imported route relay a tunnel.";
                  }
                }
              }
              container import-ribs {
                description
                  "List of imported RIBs configuration.";
                list import-rib {
                  key "source-vpn source-address-family";
                  description
                    "Configure imported RIBs.";
                  leaf source-vpn {
                    type leafref {
                      path "/ni:network-instance/ni:instances/ni:instance/ni:name";
                    }
                    must "../../../../../../../../ni:name != current()";
                    description
                      "Source VPN name.";
                  }
                  leaf source-address-family {
                    type bgp:import-rib-ipv4-safi-type;
                    description
                      "Source address family type.";
                  }
                  leaf valid-route {
                    type boolean;
                    default "false";
                    description
                      "Enable/disable imported valid route.";
                  }
                  leaf include-label-route {
                    when "../source-address-family='ipv4uni'";
                    type boolean;
                    default "false";
                    description
                      "Enable/disable imported include label route.";
                  }
                  uses choice-policy-set {
                    refine policy-type {
                      description
                        "Specify the route-policy or filter for imported RIBs.";
                    }
                  }
                }
              }
              container lsp-options {
                when "../../../../../../ni:name='_public_'";
                description
                  "Configure BGP ingress-lsp.";
                uses safi-lsp-options;
              }
              uses vrf-af-dampening-routes;
              uses bgp:slow-peer-type;
            }
            container ipv4-multicast {
              when "../type='ipv4multi'";
              description
                "Configure IPv4 multicast options.";
              container common {
                description
                  "Configure BGP IPv4-multicast address family options.";
                leaf always-compare-med {
                  type boolean;
                  default "false";
                  description
                    "Enable/disable BGP to compare the MEDs of routes from peers in different ASs in route selection. If 
                    there are multiple reachable routes to the same destination, the route with the smallest MED is preferred. Do not use this option unless different ASs use the same IGP and route selection mode.";
                }
                leaf default-med {
                  type uint32;
                  default "0";
                  description
                    "Specify the Multi-Exit-Discriminator (MED) of BGP routes. The value is an integer. This value is valid only for the imported routes and BGP summarized routes on the local router.";
                }
                leaf summary-automatic {
                  type boolean;
                  default "false";
                  description
                    "Enable/disable automatic summarization for imported routes. Manual summarization takes precedence over automatic summarization. After automatic summarization is enabled, BGP summarizes routes based on the natural network segment (for example, 10.1.1.1/24 and 10.2.1.1/24 are summarized into 10.0.0.0/8, a Class A address), and sends only the summarized route to peers. This reduces the number of routes.";
                }
                leaf bestroute-med-confederation {
                  type boolean;
                  default "false";
                  description
                    "Enable/disable BGP to compare Med value only within the federation.";
                }
                leaf default-local-preference {
                  type uint32 {
                    range "0..4294967295";
                  }
                  default "100";
                  description
                    "The local preference of BGP routes.";
                }
                leaf default-route-import {
                  type boolean;
                  default "false";
                  description
                    "Enable/disable the function to import default routes into the BGP routing table. default-route-imported must be used with import-routes so that default routes can be imported to the BGP routing table. If only import-routes is used, no default routes can be added to the BGP routing table. In addition, default-route-imported can only import the default routes in the routing table into the BGP routing table.";
                }
                leaf routerid-neglect {
                  type boolean;
                  default "false";
                  description
                    "Enable/disable BGP to ignore router IDs when selecting the optimal route. Comparing router IDs is the last resort in route selection. This means that if one optimal route must be selected and no other parameters can be used to break the tie, router IDs can be used. If this option is selected, the first received route will be selected as the optimal route, and BGP will ignore the router ID and peer address in route selection.";
                }
                leaf route-select-delay {
                  type uint16 {
                    range "0..3600";
                  }
                  units "s";
                  default "0";
                  description
                    "Route selection delay.";
                }
                uses reflect-type;
                uses reflector-cluster-type;
                leaf reflect-between-client {
                  type boolean;
                  default "true";
                  description
                    "Enable/disable route reflection between clients. If clients of a route reflector (RR) are fully meshed, you can disable route reflection among clients to reduce the cost.";
                }
                leaf determin-med {
                  type boolean;
                  default "false";
                  description
                    "Enable/disable deterministic MED so that the route selection result is relevant to the sequence in which routes are received.";
                }
                uses bestroute-med-plus-igp-type;
                uses bestroute-router-id-prior-clusterlist-type;
                leaf bestroute-as-path-ignore {
                  type boolean;
                  default "false";
                  description
                    "Enable/disable BGP to ignore the AS_Path attribute when selecting the optimal route. By default, BGP uses the AS_Path attribute as one of route selection rules, and a route with a shorter AS_Path is preferred. After bestroute-as-path-ignore is selected, BGP does not compare the AS_Path length.";
              }
                leaf bestroute-med-none-as-maximum {
                  type boolean;
                  default "false";
                  description
                    "Enable/disable BGP considers its MED as the largest MED value (4294967295). If a route does not carry MED, BGP considers its MED as the default value (0) during route selection.";
                }
                leaf maximum-load-balancing {
                  type uint16 {
                    range "1..65535";
                  }
                  must "not (../maximum-load-balancing-ibgp>1 or ../maximum-load-balancing-ebgp>1) or ../maximum-load-balancing=1";
                  default "1";
                  description
                    "Specify the maximum number of equal-cost routes in the BGP routing table. The value can be 1 or an integer greater than 1. The value depends on the associated license. By default, the maximum number of equal-cost routes is 1. Equal-cost BGP routes can be generated for load balancing only when the BGP routes meet the first nine rules of the route-selection policy and have the same AS-Path attribute.";
                }
                leaf maximum-load-balancing-ibgp {
                  type uint16 {
                    range "1..65535";
                  }
                  must "not (../maximum-load-balancing>1) or ../maximum-load-balancing-ibgp=1";
                  default "1";
                  description
                    "Specify the maximum number of equal-cost IBGP routes.";
                }
                leaf maximum-load-balancing-ebgp {
                  type uint16 {
                    range "1..65535";
                  }
                  must "not (../maximum-load-balancing>1) or ../maximum-load-balancing-ebgp=1";
                  default "1";
                  description
                    "Specify the maximum number of equal-cost EBGP routes.";
                }
                leaf ext-community-change {
                  type boolean;
                  default "false";
                  description
                    "Enable/disable the function to change the extended community attribute.";
                }
              }
              container nexthop-recursive-lookup {
                description
                  "Configure next hop iteration.";
                uses nexthop-recursive-lookup-delay;
              }
              uses bgp-route-preference-options;
              uses vrf-af-dampening-routes;
              container network-routes {
                description
                  "List of network routes.";
                list network-route {
                  key "address mask-length";
                  description
                    "Configure a network route in the BGP routing table.";
                  uses network-route-ipv4;
                }
              }
              container import-routes {
                description
                  "List of imported routes.";
                list import-route {
                  key "protocol process-id";
                  description
                    "Configure route import. Routes of other protocol types can be imported by BGP. By default, BGP does not import routes of other protocol types.";
                  leaf protocol {
                    type bgp:ipv4multi-import-route-protocol-type;
                    description
                      "Routing protocol from which routes can be imported.";
                  }
                  leaf process-id {
                    type uint32 {
                      range "0..4294967295";
                    }
                    must "((../protocol='ospf' or ../protocol='isis' or ../protocol='rip') and ../process-id!=0) or (../protocol!='ospf' and ../protocol!='isis' and ../protocol!='rip' and ../process-id=0)";
                    description
                      "Process ID of an imported routing protocol. The process ID is 0, if the imported routing protocol is direct routes, static routes, UNRs, or OP-routes. The process ID must be specified range from 1 to 4294967295, if the imported routing protocol is RIP, OSPF, ISIS.";
                  }
                  choice policy-type {
                    description
                      "Set route policy or filter.";
                    case rtp-ref {
                      description
                        "Route policy.";
                      leaf policy-name {
                        type leafref {
                          path "/rtp:routing-policy/rtp:policy-definitions/rtp:policy-definition/rtp:name";
                        }
                        description
                          "When routes are imported from other routing protocols, the route-policy filter can be used to filter the routes and change route attributes.";
                      }
                    }
                  }
                }
              }
              container aggregate-routes {
                description
                  "List of summarized routes.";
                list aggregate-route {
                  key "address mask-length";
                  description
                    "Configure a summarized route in the BGP routing table. The local outbound interface of the summarized route is Null0. When another router receives the route, the route adds an outbound interface to the route. By default, route summarization is not performed. If the Origin attributes of the specific routes for the route summarization are different, the Origin attribute of the summarized route is that with the highest priority. Origin attributes are arranged in the priority order of complete > egp > igp. A summarized route carries the community attribute of each specific route.";
                  uses unicast-aggregate-routes-type;
                }
              }
              uses ipv4-import-filter-protocol-type;
              container export-filter-policys {
                description
                  "List of filtering policies.";
                list export-filter-policy {
                  key "protocol process-id";
                  description
                    "Apply a filtering policy. It is used to filter the routes to be advertised to the peer. By default, routes are not filtered.";
                  leaf protocol {
                    type bgp:ipv4-export-filter-protocol-type;
                    description
                      "Specify the name of a routing protocol. The routing protocol takes effect only on the routes to be advertised. The IPv4 address family supports the direct, IS-IS, OSPF, RIP, and static routing protocols. The IPv6 unicast address family of a public network instance supports the direct, IS-IS, OSPFv3, RIPng, and static routing protocols. The IPv6 address family of a VPNv6 instance supports the direct, IS-IS, RIPng, and static routing protocols.";
                  }
                  leaf process-id {
                    type uint32 {
                    range "0..4294967295";
                    }
                    must "((../protocol='ospf' or ../protocol='rip' or ../protocol='isis') and ../process-id!=0) or ((../protocol!='ospf' and ../protocol!='rip' and ../protocol!='isis') and ../process-id=0)";
                    description
                      "Specify the process ID required to be matched. The value is an integer ranging from 0 to 4294967295. If direct or static routes need to be filtered, no process ID is required.";
                  }
                  uses ipv4-filter-protocol-policy-choice-type;
                }
              }
              uses bgp:slow-peer-type;
            }
          }
        }
        container peer-groups {
          description
            "List of BGP peer groups. The BGP peer groups can help you simplify the configurations. If you want to perform the same configuration for several peers, you can create a peer group and then configure the peer group. After you add these peers to the peer group, all these peers will have the same configurations as the peer group.";
          list peer-group {
            key "name";
            description
              "Configure information about a BGP peer group.";
            leaf name {
              type string {
                length "1..47";
                pattern '([^\? ]+)';
              }
              description
                "Specify the name of a peer group. The value is a string of characters, spaces not supported.";
            }
            leaf type {
              type group-type;
              mandatory true;
              description
                "Specify the type of a peer group. The value can be IBGP or EBGP.The object cannot be modified.";
              ext:operation-exclude update {
                description "The node cannot be modified, when node is already configured.";
              }
            }
            leaf local-if-name {
              type leafref {
                path "/ifm:ifm/ifm:interfaces/ifm:interface/ifm:name";
              }
              description
                "Name of a source interface that sends BGP packets. By default, the outbound interface of a BGP packet serves as the source interface of a BGP packet. To ensure that a router can send BGP packets when a physical interface fails, you can configure the source interface that sends BGP packets as a loopback interface. When using the loopback interface as the source interface, note the following points: 1. The address of the loopback interface of the BGP peer must be reachable. 2. For an EBGP connection, configure the maximum number of hops and allow EBGP peer relationships to be established in indirect mode.";
            }
            uses authentication-attr-type;
/*all product not support
            uses path-attr-map-type;
*/
            leaf description {
              type string {
                length "1..255";
                pattern '([^?]*)';
              }
              description
                "Specify the description of a peer group. The value is a string, which can be letters or digits, spaces supported. By default, no description is configured.";
            }
            leaf group-as {
              when "not(../type='ibgp')";
              type as-number-validate;
              description
                "Specify the AS number of a peer group. The AS number is in either a 2-byte or 4-byte format. 
                The two-byte format is X. X is an integer ranging from 1 to 65535.
                The four-byte format is X.Y and X. When the format is X.Y, X and Y are both integers, with the value of X ranging from 1 to 65535, and the value of Y ranging from 0 to 65535; when the format is X, X is an interger, with the value of X ranging from 1 to 4294967295.";
            }
            leaf local-if-address {
              type inet:ip-address-no-zone;
              description
                "Name of a source interface that sends BGP packets. By default, the outbound interface of a BGP packet serves as the source interface of a BGP packet. To ensure that a router can send BGP packets when a physical interface fails, you can configure the source interface that sends BGP packets as a loopback interface. When using the loopback interface as the source interface, note the following points:
                1. The address of the loopback interface of the BGP peer must be reachable.
                2. For an EBGP connection, configure the maximum number of hops and allow EBGP peer relationships to be established in indirect mode.";
            }
            leaf tcp-mss {
              type uint16 {
                range "176..4096";
              }
              description
                "Maximum TCP MSS value used for TCP connection establishment for a peer group.";
            }
            leaf ebgp-max-hop {
              when "../type='ebgp'";
              type uint32 {
                range "1..255";
              }
              must "not(../valid-ttl-hops) or (../valid-ttl-hops>=1 and not(../valid-ttl-hops>255) and ../ebgp-max-hop=1)";
              default "1";
              description
                "Maximum number of hops in an indirect EBGP connection. By default, EBGP connections can be established only between directly connected peers. The function must be configured on both ends.";
            }
            leaf valid-ttl-hops {
              type uint16 {
                range "1..255";
              }
              must "not(../ebgp-max-hop and ../ebgp-max-hop>1 and ../ebgp-max-hop<=255)";
              description
                "Enable GTSM on a peer or peer group. The valid-TTL-Value parameter is used to specify the number of TTL hops to be detected. If the value is configured as hops, the valid TTL range of the detected packet is [255-hops+1, 255].";
            }
            leaf tracking-enable {
              type boolean;
              default "false";
              description
                "Enable/disable peer tracking, After peer tracking is enabled, the device can fast detect the unreachability of a peer and reset the session.";
            }
            leaf tracking-delay-time {
              when "../tracking-enable='true'";
              type uint16;
              units "s";
              default "0";
              description
                "Specify the delay to reset the session.";
            }
            leaf conventional {
              type boolean;
              default "false";
              description
                "Enable/disable general router functions on peers. In conventional mode, not all the extended router functions, such as, route refreshing, GR, and multi-address family negotiation, are available. Therefore, the router of a new version can be compatible with the routers of earlier versions.";
            }
            leaf route-refresh {
              type boolean;
              default "true";
              description
                "Enable/disable BGP to advertise Refresh messages to peers.";
            }
            leaf four-byte-as {
              type boolean;
              default "true";
              description
                "Enable/disable BGP to advertise routes carrying 4-byte AS numbers to peers. After the 4-byte AS number function is disabled, Open packets will not carry 4-byte AS number capability flag, and peer ends will not know that local ends have the 4-byte AS number function. The 4-byte AS number function cannot be disabled from peers (peer groups) if a 4-byte AS number, fake AS number, or confederation ID is configured on a router and the AS number of a peer is 4-byte. If the 4-byte AS number function is disabled in such a situation, BGP sessions may fail to be established, and route transmission may be affected.";
            }
            leaf ignore {
              type boolean;
              default "false";
              description
                "Enable/disable the function to tear down sessions between peers and clear all related routing information.";
            }
            leaf connect-mode {
              type connect-mode;
              default "null";
              description
                "The value can be Connect-only, Listen-only, or Both. If the value is Connect-only, the specified peer or peer group only initiatively sends connection requests, instead of listening to connection requests. If the value is Listen-only, the specified peer or peer group only listens to connection requests, instead of initiatively sending connection requests. If the value is Both, the specified peer or peer group not only initiatively sends connection requests, but also listens to connection requests. The default value is Both.";
            }
            leaf log-change {
              type boolean;
              default "true";
              description
                "Enable/disable BGP to record the session status and events of the specified peer or peer group.";
            }
            leaf path-mtu-auto-discovery {
              type boolean;
              default "false";
              description
                "Enable/disable path mtu auto discovery.";
            }
            leaf local-ifnet-disable {
              when "../../../../../ni:name='_public_'";
              type boolean;
              description
                "Enable/disable MPLS local IFNET tunnel creation on a BGP peer. By default, MPLS local IFNET tunnels can be created on an EBGP peer,but such tunnels cannot be created on an IBGP peer.";
              ext:dynamic-default;
            }
            leaf check-first-as {
              when "../type='ebgp'";
              type peer-cap-config-state;
              default "default";
              description
                "Check the first AS in the AS_Path of the update messages from EBGP peers.";
            }
            leaf memory-priority {
              type memory-priority;
              default "medium";
              description
                "Set a priority that determines the disconnection order of each BGP peer relationship in a peer group if memory overload occurs.";
            }
            container fake-as-parameter {
              description
                "Configure BGP fake-as parameters.";
              leaf fake-as {
                when "../../bgp:type='ebgp'";
                type bgp:as-number-validate;
                description
                  "Fake AS number that is specified for a local peer. By default, a peer uses the actual AS number of the local end.
                  An AS number can be in either two-byte format or four-byte format:
                  The two-byte format is X. X is an integer ranging from 1 to 65535.
                  The four-byte format is X.Y and X. When the format is X.Y, X and Y are both integers, with the value of X ranging from 1 to 65535, and the value of Y ranging from 0 to 65535; when the format is X, X is an interger, with the value of X ranging from 1 to 4294967295.";
              }
              leaf dual-as {
                when "../fake-as";
                type boolean;
                default "false";
                description
                  "Enable/disable the function to the remote EBGP peer can use the actual or fake AS number when specifying the AS number for a local peer. The local peer uses the fake and actual AS numbers to establish a BGP peer relationship with the remote end and identifies the AS number configured by the remote end through the error code (OPEN Message Error) and sub-error code (Bad Peer AS) of the Notification message from the remote end.";
              }
              leaf prepend-global-as {
                when "../fake-as";
                type boolean;
                default "false";
                description
                  "Enable/disable the function to add the global AS number to the Update packets to be advertised.";
              }
              leaf prepend-fake-as {
                when "../fake-as";
                type boolean;
                default "false";
                description
                  "Enable/disable the function to add the Fake AS number to received Update packets.";
              }
            }
            uses peer-timer-para-type;
            container bfd-parameter {
              description
                "Configure BFD.";
              leaf enable {
                type boolean;
                default "false";
                description
                  "Enable/disable BFD.";
              }
              choice mode-type {
                description
                  "Set bfd mode.";
                case single {
                  description
                    "Single hop mode.";
                  leaf single-hop {
                    when "../enable='true'";
                    type empty;
                    description
                      "The single hop mode is preferred during the BFD session establishment between IBGP peers.";
                  }
                  leaf compatible {
                    when "../enable='true'";
                    type empty;
                    description
                      "Compatible.";
                  }
                }
                case link {
                  description
                    "Per-link-echo mode.";
                  leaf per-link-echo {
                    when "../enable='true'";
                    type empty;
                    description
                      "The per-link one-arm-echo mode is preferred during the BFD session establishment between IBGP peers.";
                  }
                }
              }
              uses bfd-detect-parameter-type;
            }
            container graceful-restart {
              description
                "Configure graceful restart.";
              uses group-graceful-restart-type;
              leaf peer-reset {
                type boolean;
                default "false";
                description
                  "Enable/disable reseting BGP peer graceful.";
              }
            }
            container local-graceful-restart {
              description
                "Configure local graceful restart.";
              uses group-graceful-restart-type;
            }
            container members {
              config false;
              description
                "List of members in a peer group.";
              list member {
                key "peer-address";
                config false;
                description
                  "Statistics of member in a peer group.";
                leaf peer-address {
                  type inet:ip-address-no-zone;
                  config false;
                  description
                    "Specify the address of the peer joining the peer group.";
                }
              }
            }
            container afs {
              description
                "List of all peer groups that are enabled in a specified address family.";
              list af {
                key "type";
                description
                  "Configure peer group enabled in a specified address family.";
                leaf type {
                  type bgp:group-af-type;
                  must "../../../../../afs/af[type = current()]";
                  description
                    "Address family type of a BGP instance.";
                }
                container ipv4-unicast {
                  when "../type = 'ipv4uni'";
                  description
                    "Configure IPv4 unicast options.";
                  leaf advertise-community {
                    type boolean;
                    default "false";
                    description
                      "Enable/disable advertise the community attribute to a peer or a peer group.";
                  }
                  leaf reflect-client {
                    when "../../../../bgp:type='ibgp'";
                    type boolean;
                    default "false";
                    description
                      "Enable/disable the local device as a route reflector (RR) and a peer or peer group as its client. This configuration is applicable between IBGP peers only. The configurations of RRs and its clients in an address family are valid only in this address family. Therefore, it is recommended to configure RRs and its clients in the specified address family that is required.";
                  }
                  leaf orf-type {
                    when "../../../../../../../../ni:name='_public_'";
                    type bgp:bgp-orf-type;
                    must "(../orf-mode='null' and ../orf-type='null') or (../orf-mode!='null' and ../orf-type!='null')";
                    default "null";
                    description
                      "ORF Type.";
                  }
                  leaf orf-mode {
                    when "../../../../../../../../ni:name='_public_'";
                    type bgp:bgp-orf-mode-type;
                    must "(../orf-mode='null' and ../orf-type='null') or (../orf-mode!='null' and ../orf-type!='null')";
                    default "null";
                    description
                      "Configure an outbound route filtering (ORF) mode, which can be Receive, Send, or Both, and the default ORF mode is Both.";
                  }
                  leaf label-route-capability {
                    type boolean;
                    default "false";
                    description
                      "Enable/disable a device to exchange labeled routes.";
                  }
                  leaf check-tunnel-reachable {
                    when "../label-route-capability='true'";
                    type boolean;
                    default "false";
                    description
                      "Enable/disable tunnel reachability check.";
                  }
                  leaf check-withdraw-type {
                    when "../label-route-capability='true'";
                    type boolean;
                    default "true";
                    description
                      "Enable/disable withdraw type check.";
                  }
                  leaf nexthop-configure {
                    type nexthop-configuration-type;
                    description
                      "Both the next-hop-local mode and next-hop-invariable mode are available when the peer address family is the VPNv4/VPNv6/L2VPN AD address family. Only the next-hop-local mode is available when the peer address family is not VPNv4/VPNV6/L2VPN AD address family. In next-hop-local mode, you can configure a BGP speaker to set its IP address of as the next hop of the routes to be advertised to IBGP peers or IBGP peer groups. In next-hop-invariable mode, you can configure PEs in different ASs not to change the next hop of routes when the PEs advertise the routes to their EBGP peers and use the next hop addresses of IGP routes to advertise imported IGP routes to IBGP peers. By default, when a BGP speaker advertises routes to EBGP peers and imported IGP routes to IBGP peers, the BGP speaker changes the next hop to its interface address.";
                  }
                  choice import-policy-type {
                    description
                      "Set route policy or filter.";
                    case rtp-ref {
                      description
                        "Route policy.";
                      leaf import-policy {
                        type leafref {
                          path "/rtp:routing-policy/rtp:policy-definitions/rtp:policy-definition/rtp:name";
                        }
                        description
                          "Specify the filtering policy applied to the routes learned from a peer. By default, no such policy is specified.";
                      }
                    }
                    case xpl-ref {
                      description
                        "Route filter.";
                      container import-filter {
                        description
                          "Configure an import route-filter to filter the routes received from a peer group. By default, no route-filter is specified to filter the routes imported from a peer group.";
                        leaf name {
                          type leafref {
                            path "/xpl:xpl/xpl:route-filters/xpl:route-filter/xpl:name";
                          }
                          description
                            "Specify an import route-filter name.";
                        }
                        leaf parameter {
                          when "../name";
                          type string {
                            length "1..1609";
                          }
                          description
                            "Specify an import route-filter parameter.";
                        }
                      }
                    }
                  }
                  choice export-policy-type {
                    description
                      "Set route policy or filter.";
                    case rtp-ref {
                      description
                        "Route policy.";
                      leaf export-policy {
                        type leafref {
                          path "/rtp:routing-policy/rtp:policy-definitions/rtp:policy-definition/rtp:name";
                        }
                        description
                          "Specify the filtering policy applied to the routes to be advertised to a peer. By default, no such policy is specified.";
                      }
                    }
                    case xpl-ref {
                      description
                        "Route filter.";
                      container export-filter {
                        description
                          "Configure an export route-filter to filter the routes to be advertised to a peer group. By default, no route-filter is specified to filter the routes to be advertised to a peer group.";
                        leaf name {
                          type leafref {
                            path "/xpl:xpl/xpl:route-filters/xpl:route-filter/xpl:name";
                          }
                          description
                            "Specify an export route-filter name.";
                        }
                        leaf parameter {
                          when "../name";
                          type string {
                            length "1..1609";
                          }
                          description
                            "Specify an export route-filter parameter.";
                        }
                      }
                    }
                  }
                  leaf advertise-ext-community {
                    type boolean;
                    default "false";
                    description
                      "Enable/disable advertise the extended community attribute to a peer or peer group.";
                  }
                  leaf discard-ext-community {
                    type boolean;
                    default "false";
                    description
                      "Enable/disable discard the extended community attribute in the routing information about a specified peer.";
                  }
                  leaf allow-as-loop {
                    type uint32 {
                      range "1..10";
                    }
                    description
                      "Allow repetitive local AS numbers. By default, repetitive local AS numbers are not allowed.";
                  }
                  leaf aigp {
                    when "../../../../../../../../ni:name='_public_'";
                    type boolean;
                    default "false";
                    description
                      "Enable/disable route with AIGP attribute advertisement to or from a peer.";
                  }
                  leaf add-path-mode {
                    when "../../../../../../../../ni:name='_public_' and ../../../../bgp:type='ibgp'";
                    type add-path-cap-type;
                    default "null";
                    description
                      "Enable Add-Path route advertisement to a peer.";
                  }
                  uses ip-prefix-filter-type;
                  uses as-path-filter-type;
                  uses default-route-advertise-type;
                  leaf default-route-match-mode {
                    when "../default-route-advertise='true'";
                    type cra-match-mode;
                    default "null";
                    description
                      "Configure the matching mode of default route advertisement, which can be disabling of route advertisement conditions, enabling of all route advertisement conditions, and enabling of part route advertisement conditions. Enabling of all route advertisement conditions indicates that a default route can be advertised only when it matches all the conditions. Enabling of part route advertisement conditions indicates that a default route can be advertised only when it matches one condition.";
                  }
                  uses rt-update-interval-type;
                  uses preferred-value-type;
                  leaf add-path-number {
                    when "../../../../../../../../ni:name='_public_' and ../../../../bgp:type='ibgp'";
                    type uint8 {
                      range "2..64";
                    }
                    description
                      "Number of Add-Path routes that can be advertised to a peer.";
                  }
                  leaf substitute-as-enable {
                    when "../../../../bgp:type='ebgp'";
                    type boolean;
                    default "false";
                    description
                      "Enable/disable replace the AS number of a specified peer in the AS_Path attribute with the local AS number. On a PE where AS number replacement is enabled, if an AS number in the AS_Path attribute of a route is same as that of the CE to which the PE advertises the route, the PE replaces the AS number with its own AS number before advertising the route.";
                  }
                  leaf soo {
                    when "../../../../../../../../ni:name!='_public_'";
                    type string {
                      length "3..21";
                    }
                    description
                      "Configure the Site-of-Origin (SoO) extended community attribute. This attribute can be expressed in the following formats: X.X.X.X:number<0-65535>, number<0-65535>:number<0-4294967295>, or number<0-65535>.number<0-65535>:number<0-65535> or <65536-4294967295>:<0-65535>. 0:0 or 0.0:0 is not supported. 
                      Two CEs are in the same site and can advertise routes to each other, and they are connected to a VPN through PEs. If the local routes of a CE are advertised to the other CE over the VPN, a routing loop may occur. 
                      The SoO feature can prevent a route advertised by a site from being sent back to the site, preventing routing loops. After SoO is enabled and a PE receives a route from a CE, the specified SoO attribute will be added to the route. Before advertising the route to the other CE, the PE checks the SoO attribute. If the SoO attribute is the same as the locally configured SoO attribute, the PE does not advertise the route, preventing routing loops.";
                  }
                  leaf keep-all-routes {
                    when "/bgp:bgp/bgp:base-process/bgp:keep-all-routes='false'";
                    type boolean;
                    default "false";
                    description
                      "Enable/disable saving all the updated information about BGP routes from a specified peer or peer group after a BGP connection is established, even though these BGP routes fail to match the routing policy on the ingress. By default, the updated information about BGP routes from a specified peer is saved only when the routes match the routing policy on the ingress. If a router supports route refreshing, this option is not required.";
                  }
                  leaf exp-mode {
                    when "../../../../../../../../ni:name='_public_'";
                    type exp-mode-type;
                    default "null";
                    description
                      "Specify the ASs in which a BGP label can inherit the QoS priority carried in the outer label of public tunnel in the Core AS and the ASs in which the priorities of BGP LSPs must be restored before the LSPs are advertised to a non-core AS.";
                  }
                  leaf advertise-best-external {
                    when "../../../../../../../../ni:name='_public_' and ../../../../bgp:type='ibgp'";
                    type boolean;
                    must "../reflect-client='false' or ../advertise-best-external='false'";
                    must "../add-path-mode='null' or not(../add-path-mode) or ../advertise-best-external='false'";
                    must "not(../add-path-number and ../advertise-best-external='true')";
                    default "false";
                    description
                      "Enable/disable the device to advertise Best External routes to peers.";
                  }
                  leaf load-balancing-enable {
                    type boolean;
                    default "false";
                    description
                      "Enable/disable a neighbour to participate in load balancing.";
                  }
                  choice load-balancing-ignore-as-type {
                    description
                      "Set load balancing as path type.";
                    case as-attribute {
                      description
                        "Ignore the as-path attribute.";
                      leaf load-balancing-as-path-ignore {
                        when "../load-balancing-enable='true'";
                        type empty;
                        description
                          "Configure BGP to ignore the AS_Path attribute when selecting the equal route. After as-path-neglect is selected, BGP does not compare the AS_Path length.";
                      }
                    }
                    case same-length-as-attribute {
                      description
                        "Ignore comparison of as-path attributes with the same length.";
                      leaf load-balancing-as-path-relax {
                        when "../load-balancing-enable='true'";
                        type empty;
                        description
                          "Configure BGP to ignore comparison of AS_Path attributes with the same length when selecting the equal route. After as-path-neglect is selected, BGP does not compare the AS_Path length.";
                      }
                    }
                  }
                  leaf prefix-sid {
                    when "../../../../../../../../ni:name='_public_'";
                    type boolean;
                    default "false";
                    description
                      "Enable/disable a device to exchange IPv4 prefix SIDs with a specified IPv6 peer group.";
                  }
                  uses advertise-large-community-group-type;
                  uses ipv4-default-route-match-conditions-type;
                  uses route-limit-accept-type;
                  uses public-as-only-type;
                  container entropy-label-parameter {
                    when "../../../../../../../../ni:name='_public_' and ../label-route-capability='true'";
                    description
                      "Configure information about entropy label parameter in a peer group.";
                    uses group-entropy-label-type;
                  }
                }
                container ipv6-unicast {
                  when "../type = 'ipv6uni'";
                  description
                    "Configure IPv6 unicast options.";
                  leaf advertise-community {
                    type boolean;
                    default "false";
                    description
                      "Enable/disable advertise the community attribute to a peer or a peer group.";
                  }
                  leaf reflect-client {
                    when "../../../../bgp:type='ibgp'";
                    type boolean;
                    default "false";
                    description
                      "Enable/disable the local device as a route reflector (RR) and a peer or peer group as its client. This configuration is applicable between IBGP peers only. The configurations of RRs and its clients in an address family are valid only in this address family. Therefore, it is recommended to configure RRs and its clients in the specified address family that is required.";
                  }
                  leaf label-route-capability {
                    type boolean;
                    default "false";
                    description
                      "Enable/disable a device to exchange labeled routes.";
                  }
                  leaf nexthop-configure {
                    type nexthop-configuration-type;
                    description
                      "Both the next-hop-local mode and next-hop-invariable mode are available when the peer address family is the VPNv4/VPNV6/L2VPN AD address family. Only the next-hop-local mode is available when the peer address family is not VPNv4/VPNV6/L2VPN AD address family. In next-hop-local mode, you can configure a BGP speaker to set its IP address of as the next hop of the routes to be advertised to IBGP peers or IBGP peer groups. In next-hop-invariable mode, you can configure PEs in different ASs not to change the next hop of routes when the PEs advertise the routes to their EBGP peers and use the next hop addresses of IGP routes to advertise imported IGP routes to IBGP peers. By default, when a BGP speaker advertises routes to EBGP peers and imported IGP routes to IBGP peers, the BGP speaker changes the next hop to its interface address.";
                  }
                  choice import-policy-type {
                    description
                      "Set route policy or filter.";
                    case rtp-ref {
                      description
                        "Route policy.";
                      leaf import-policy {
                        type leafref {
                          path "/rtp:routing-policy/rtp:policy-definitions/rtp:policy-definition/rtp:name";
                        }
                        description
                          "Specify the filtering policy applied to the routes learned from a peer. By default, no such policy is specified.";
                      }
                    }
                  }
                  choice export-policy-type {
                    description
                      "Set route policy or filter.";
                    case rtp-ref {
                      description
                        "Route policy.";
                      leaf export-policy {
                        type leafref {
                          path "/rtp:routing-policy/rtp:policy-definitions/rtp:policy-definition/rtp:name";
                        }
                        description
                          "Specify the filtering policy applied to the routes to be advertised to a peer. By default, no such policy is specified.";
                      }
                    }
                  }
                  leaf advertise-ext-community {
                    type boolean;
                    default "false";
                    description
                      "Enable/disable advertise the extended community attribute to a peer or peer group.";
                  }
                  leaf discard-ext-community {
                    type boolean;
                    default "false";
                    description
                      "Enable/disable discard the extended community attribute in the routing information about a specified peer.";
                  }
                  leaf allow-as-loop {
                    type uint32 {
                      range "1..10";
                    }
                    description
                      "Allow repetitive local AS numbers. By default, repetitive local AS numbers are not allowed.";
                  }
                  leaf aigp {
                    when "../../../../../../../../ni:name='_public_'";
                    type boolean;
                    default "false";
                    description
                      "Enable/disable route with AIGP attribute advertisement to or from a peer.";
                  }
                  uses default-route-advertise-type;
                  leaf default-route-match-mode {
                    when "../default-route-advertise='true'";
                    type cra-match-mode;
                    default "null";
                    description
                      "Configure the matching mode of default route advertisement, which can be disabling of route advertisement conditions, enabling of all route advertisement conditions, and enabling of part route advertisement conditions. Enabling of all route advertisement conditions indicates that a default route can be advertised only when it matches all the conditions. Enabling of part route advertisement conditions indicates that a default route can be advertised only when it matches one condition.";
                  }
                  leaf add-path-mode {
                    when "../../../../../../../../ni:name='_public_' and ../../../../bgp:type='ibgp'";
                    type add-path-cap-type;
                    default "null";
                    description
                      "Enable Add-Path route advertisement to a peer.";
                  }
                  uses ipv6-prefix-filter-type;
                  uses as-path-filter-type;
                  uses rt-update-interval-type;
                  uses preferred-value-type;
                  leaf add-path-number {
                    when "../../../../../../../../ni:name='_public_' and ../../../../bgp:type='ibgp'";
                    type uint8 {
                      range "2..64";
                    }
                    description
                      "Number of Add-Path routes that can be advertised to a peer.";
                  }
                  leaf substitute-as-enable {
                    when "../../../../bgp:type='ebgp'";
                    type boolean;
                    default "false";
                    description
                      "Enable/disable replace the AS number of a specified peer in the AS_Path attribute with the local AS number. On a PE where AS number replacement is enabled, if an AS number in the AS_Path attribute of a route is same as that of the CE to which the PE advertises the route, the PE replaces the AS number with its own AS number before advertising the route.";
                  }
                  leaf soo {
                    when "../../../../../../../../ni:name!='_public_'";
                    type string {
                      length "3..21";
                    }
                    description
                      "Configure the Site-of-Origin (SoO) extended community attribute. This attribute can be expressed in the following formats: X.X.X.X:number<0-65535>, number<0-65535>:number<0-4294967295>, or number<0-65535>.number<0-65535>:number<0-65535> or <65536-4294967295>:<0-65535>. 0:0 or 0.0:0 is not supported. 
                      Two CEs are in the same site and can advertise routes to each other, and they are connected to a VPN through PEs. If the local routes of a CE are advertised to the other CE over the VPN, a routing loop may occur. 
                      The SoO feature can prevent a route advertised by a site from being sent back to the site, preventing routing loops. After SoO is enabled and a PE receives a route from a CE, the specified SoO attribute will be added to the route. Before advertising the route to the other CE, the PE checks the SoO attribute. If the SoO attribute is the same as the locally configured SoO attribute, the PE does not advertise the route, preventing routing loops.";
                  }
                  leaf keep-all-routes {
                    when "/bgp:bgp/bgp:base-process/bgp:keep-all-routes='false'";
                    type boolean;
                    default "false";
                    description
                      "Enable/disable saving all the updated information about BGP routes from a specified peer or peer group after a BGP connection is established, even though these BGP routes fail to match the routing policy on the ingress. By default, the updated information about BGP routes from a specified peer is saved only when the routes match the routing policy on the ingress. If a router supports route refreshing, this option is not required.";
                  }
                  leaf advertise-best-external {
                    when "../../../../../../../../ni:name='_public_' and ../../../../bgp:type='ibgp'";
                    type boolean;
                    must "../reflect-client='false' or ../advertise-best-external='false'";
                    must "../add-path-mode='null' or not(../add-path-mode) or ../advertise-best-external='false'";
                    must "not(../add-path-number and ../advertise-best-external='true')";
                    default "false";
                    description
                      "Enable/disable the device to advertise Best External routes to peers.";
                  }
                  leaf load-balancing-enable {
                    type boolean;
                    default "false";
                    description
                      "Enable/disable a neighbour to participate in load balancing.";
                  }
                  choice load-balancing-ignore-as-type {
                    description
                      "Set load balancing as path type.";
                    case as-attribute {
                      description
                        "Ignore the as-path attribute.";
                      leaf load-balancing-as-path-ignore {
                        when "../load-balancing-enable='true'";
                        type empty;
                        description
                          "Configure BGP to ignore the AS_Path attribute when selecting the equal route. After as-path-neglect is selected, BGP does not compare the AS_Path length.";
                      }
                    }
                    case same-length-as-attribute {
                      description
                        "Ignore comparison of as-path attributes with the same length.";
                      leaf load-balancing-as-path-relax {
                        when "../load-balancing-enable='true'";
                        type empty;
                        description
                          "Configure BGP to ignore comparison of AS_Path attributes with the same length when selecting the equal route. After as-path-neglect is selected, BGP does not compare the AS_Path length.";
                      }
                    }
                  }
                  leaf prefix-sid {
                    when "../../../../../../../../ni:name='_public_'";
                    type boolean;
                    default "false";
                    description
                      "Enable/disable a device to exchange IPv4 prefix SIDs with a specified IPv6 peer group.";
                  }
                  uses advertise-large-community-group-type;
                  uses ipv6-default-route-match-conditions-type;
                  uses route-limit-accept-type;
                  uses public-as-only-type;
                }
                container ipv4-vpn {
                  when "../type = 'ipv4vpn'";
                  description
                    "Configure IPv4 vpnv4 options.";
                  leaf advertise-community {
                    type boolean;
                    default "false";
                    description
                      "Enable/disable advertise the community attribute to a peer or a peer group.";
                  }
                  leaf reflect-client {
                    when "../../../../bgp:type='ibgp'";
                    type boolean;
                    default "false";
                    description
                      "Enable/disable the local device as a route reflector (RR) and a peer or peer group as its client. This configuration is applicable between IBGP peers only. The configurations of RRs and its clients in an address family are valid only in this address family. Therefore, it is recommended to configure RRs and its clients in the specified address family that is required.";
                  }
                  leaf nexthop-configure {
                    type nexthop-configuration-type;
                    description
                      "Both the next-hop-local mode and next-hop-invariable mode are available when the peer address family is the VPNv4/VPNV6/L2VPN AD address family. Only the next-hop-local mode is available when the peer address family is not VPNv4/VPNV6/L2VPN AD address family. In next-hop-local mode, you can configure a BGP speaker to set its IP address of as the next hop of the routes to be advertised to IBGP peers or IBGP peer groups. In next-hop-invariable mode, you can configure PEs in different ASs not to change the next hop of routes when the PEs advertise the routes to their EBGP peers and use the next hop addresses of IGP routes to advertise imported IGP routes to IBGP peers. By default, when a BGP speaker advertises routes to EBGP peers and imported IGP routes to IBGP peers, the BGP speaker changes the next hop to its interface address.";
                  }
                  choice import-policy-type {
                    description
                      "Set route policy or filter.";
                    case rtp-ref {
                      description
                        "Route policy.";
                      leaf import-policy {
                        type leafref {
                          path "/rtp:routing-policy/rtp:policy-definitions/rtp:policy-definition/rtp:name";
                        }
                        description
                          "Specify the filtering policy applied to the routes learned from a peer. By default, no such policy is specified.";
                      }
                    }
                  }
                  choice export-policy-type {
                    description
                      "Set route policy or filter.";
                    case rtp-ref {
                      description
                        "Route policy.";
                      leaf export-policy {
                        type leafref {
                          path "/rtp:routing-policy/rtp:policy-definitions/rtp:policy-definition/rtp:name";
                        }
                        description
                          "Specify the filtering policy applied to the routes to be advertised to a peer. By default, no such policy is specified.";
                      }
                    }
                  }
                  leaf allow-as-loop {
                    type uint32 {
                      range "1..10";
                    }
                    description
                      "Allow repetitive local AS numbers. By default, repetitive local AS numbers are not allowed.";
                  }
                  leaf aigp {
                    type boolean;
                    default "false";
                    description
                      "Enable/disable route with AIGP attribute advertisement to or from a peer.";
                  }
                  leaf add-path-mode {
                    when "../../../../bgp:type='ibgp'";
                    type add-path-cap-type;
                    default "null";
                    description
                      "Enable Add-Path route advertisement to a peer.";
                  }
                  uses ip-prefix-filter-type;
                  leaf reoriginate-route-enable {
                    type boolean;
                    default "false";
                    description
                      "Enable/disable route regeneration.";
                  }
                  leaf reoriginate-ip-enable {
                    type boolean;
                    default "false";
                    description
                      "Enable/disable IP route regeneration and advertisement.";
                  }
                  leaf reoriginate-mac-ip-enable {
                    type boolean;
                    default "false";
                    description
                      "Enable/disable MAC-IP route regeneration and advertisement.";
                  }
                  leaf reoriginate-vpnv4-route-enable {
                    type boolean;
                    default "false";
                    description
                       "Enable/disable VPNv4 route regeneration and advertisement.";
                  }
                  uses as-path-filter-type;
                  uses rt-update-interval-type;
                  uses preferred-value-type;
                  leaf add-path-number {
                    when "../../../../bgp:type='ibgp'";
                    type uint8 {
                      range "2..64";
                    }
                    description
                      "Number of Add-Path routes that can be advertised to a peer.";
                  }
                  leaf upe {
                    type boolean;
                    default "false";
                    description
                      "Enable/disable the peer as an underlayer PE (UPE).";
                  }
                  leaf advertise-best-external {
                    when "../../../../bgp:type='ibgp'";
                    type boolean;
                    must "../reflect-client='false' or ../advertise-best-external='false'";
                    must "../add-path-mode='null' or not(../add-path-mode) or ../advertise-best-external='false'";
                    must "not(../add-path-number and ../advertise-best-external='true')";
                    default "false";
                    description
                      "Enable/disable the device to advertise Best External routes to peers.";
                  }
                  uses advertise-large-community-group-type;
                  leaf keep-all-routes {
                    when "/bgp:bgp/bgp:base-process/bgp:keep-all-routes='false'";
                    type boolean;
                    default "false";
                    description
                      "Enable/disable saving all the updated information about BGP routes from a specified peer or peer group after a BGP connection is established, even though these BGP routes fail to match the routing policy on the ingress. By default, the updated information about BGP routes from a specified peer is saved only when the routes match the routing policy on the ingress. If a router supports route refreshing, this option is not required.";
                  }
                  container default-route-originates {
                    description
                      "Configure advertised default VPNv4 routes.";
                    uses default-route-originate-type;
                  }
                  uses route-limit-type;
                  uses public-as-only-type;
                }
                container ipv6-vpn {
                  when "../type = 'ipv6vpn'";
                  description
                    "Configure IPv6 vpn options.";
                  leaf advertise-community {
                    type boolean;
                    default "false";
                    description
                      "Enable/disable advertise the community attribute to a peer or a peer group.";
                  }
                  leaf reflect-client {
                    when "../../../../bgp:type='ibgp'";
                    type boolean;
                    default "false";
                    description
                      "Enable/disable the local device as a route reflector (RR) and a peer or peer group as its client. This configuration is applicable between IBGP peers only. The configurations of RRs and its clients in an address family are valid only in this address family. Therefore, it is recommended to configure RRs and its clients in the specified address family that is required.";
                  }
                  leaf nexthop-configure {
                    type nexthop-configuration-type;
                    description
                      "Both the next-hop-local mode and next-hop-invariable mode are available when the peer address family is the VPNv4/VPNV6/L2VPN AD address family. Only the next-hop-local mode is available when the peer address family is not VPNv4/VPNV6/L2VPN AD address family. In next-hop-local mode, you can configure a BGP speaker to set its IP address of as the next hop of the routes to be advertised to IBGP peers or IBGP peer groups. In next-hop-invariable mode, you can configure PEs in different ASs not to change the next hop of routes when the PEs advertise the routes to their EBGP peers and use the next hop addresses of IGP routes to advertise imported IGP routes to IBGP peers. By default, when a BGP speaker advertises routes to EBGP peers and imported IGP routes to IBGP peers, the BGP speaker changes the next hop to its interface address.";
                  }
                  choice import-policy-type {
                    description
                      "Set route policy or filter.";
                    case rtp-ref {
                      description
                        "Route policy.";
                      leaf import-policy {
                        type leafref {
                          path "/rtp:routing-policy/rtp:policy-definitions/rtp:policy-definition/rtp:name";
                        }
                        description
                          "Specify the filtering policy applied to the routes learned from a peer. By default, no such policy is specified.";
                      }
                    }
                  }
                  choice export-policy-type {
                    description
                      "Set route policy or filter.";
                    case rtp-ref {
                      description
                        "Route policy.";
                      leaf export-policy {
                        type leafref {
                          path "/rtp:routing-policy/rtp:policy-definitions/rtp:policy-definition/rtp:name";
                        }
                        description
                          "Specify the filtering policy applied to the routes to be advertised to a peer. By default, no such policy is specified.";
                      }
                    }
                  }
                  leaf allow-as-loop {
                    type uint32 {
                      range "1..10";
                    }
                    description
                      "Allow repetitive local AS numbers. By default, repetitive local AS numbers are not allowed.";
                  }
                  leaf aigp {
                    type boolean;
                    default "false";
                    description
                      "Enable/disable route with AIGP attribute advertisement to or from a peer.";
                  }
                  leaf add-path-mode {
                    when "../../../../bgp:type='ibgp'";
                    type add-path-cap-type;
                    default "null";
                    description
                      "Enable Add-Path route advertisement to a peer.";
                  }
                  uses ipv6-prefix-filter-type;
                  leaf reoriginate-route-enable {
                    type boolean;
                    default "false";
                    description
                      "Enable/disable route regeneration.";
                  }
                  leaf reoriginate-ipv6-enable {
                    type boolean;
                    default "false";
                    description
                      "Enable/disable IP route regeneration and advertisement.";
                  }
                  leaf reoriginate-mac-ipv6-enable {
                    type boolean;
                    default "false";
                    description
                      "Enable/disable MAC-IP route regeneration and advertisement.";
                  }
                  uses as-path-filter-type;
                  uses rt-update-interval-type;
                  uses preferred-value-type;
                  leaf add-path-number {
                    when "../../../../bgp:type='ibgp'";
                    type uint8 {
                      range "2..64";
                    }
                    description
                      "Number of Add-Path routes that can be advertised to a peer.";
                  }
                  leaf advertise-best-external {
                    when "../../../../bgp:type='ibgp'";
                    type boolean;
                    must "../reflect-client='false' or ../advertise-best-external='false'";
                    must "../add-path-mode='null' or not(../add-path-mode) or ../advertise-best-external='false'";
                    must "not(../add-path-number and ../advertise-best-external='true')";
                    default "false";
                    description
                      "Enable/disable the device to advertise Best External routes to peers.";
                  }
                  uses advertise-large-community-group-type;
                  leaf keep-all-routes {
                    when "/bgp:bgp/bgp:base-process/bgp:keep-all-routes='false'";
                    type boolean;
                    default "false";
                    description
                      "Enable/disable saving all the updated information about BGP routes from a specified peer or peer group after a BGP connection is established, even though these BGP routes fail to match the routing policy on the ingress. By default, the updated information about BGP routes from a specified peer is saved only when the routes match the routing policy on the ingress. If a router supports route refreshing, this option is not required.";
                  }
                  uses route-limit-type;
                  uses public-as-only-type;
                }
                container ipv4-labeluni {
                  when "../type = 'ipv4labeluni'";
                  description
                    "Configure IPv4 label unicast options.";
                  leaf advertise-community {
                    type boolean;
                    default "false";
                    description
                      "Enable/disable advertise the community attribute to a peer or a peer group.";
                  }
                  leaf reflect-client {
                    when "../../../../bgp:type='ibgp'";
                    type boolean;
                    default "false";
                    description
                      "Enable/disable the local device as a route reflector (RR) and a peer or peer group as its client. This configuration is applicable between IBGP peers only. The configurations of RRs and its clients in an address family are valid only in this address family. Therefore, it is recommended to configure RRs and its clients in the specified address family that is required.";
                  }
                  leaf check-tunnel-reachable {
                    type boolean;
                    default "false";
                    description
                      "Enable/disable tunnel reachability check.";
                  }
                  choice import-policy-type {
                    description
                      "Set route policy or filter.";
                    case rtp-ref {
                      description
                        "Route policy.";
                      leaf import-policy {
                        type leafref {
                          path "/rtp:routing-policy/rtp:policy-definitions/rtp:policy-definition/rtp:name";
                        }
                        description
                          "Specify the filtering policy applied to the routes learned from a peer. By default, no such policy is specified.";
                      }
                    }
                  }
                  choice export-policy-type {
                    description
                      "Set route policy or filter.";
                    case rtp-ref {
                      description
                        "Route policy.";
                      leaf export-policy {
                        type leafref {
                          path "/rtp:routing-policy/rtp:policy-definitions/rtp:policy-definition/rtp:name";
                        }
                        description
                          "Specify the filtering policy applied to the routes to be advertised to a peer. By default, no such policy is specified.";
                      }
                    }
                  }
                  leaf advertise-ext-community {
                    type boolean;
                    default "false";
                    description
                      "Enable/disable advertise the extended community attribute to a peer or peer group.";
                  }
                  leaf discard-ext-community {
                    type boolean;
                    default "false";
                    description
                      "Enable/disable discard the extended community attribute in the routing information about a specified peer.";
                  }
                  leaf allow-as-loop {
                    type uint32 {
                      range "1..10";
                    }
                    description
                      "Allow repetitive local AS numbers. By default, repetitive local AS numbers are not allowed.";
                  }
                  leaf aigp {
                    when "../../../../../../../../ni:name='_public_'";
                    type boolean;
                    default "false";
                    description
                      "Enable/disable route with AIGP attribute advertisement to or from a peer.";
                  }
                  leaf add-path-mode {
                    when "../../../../../../../../ni:name='_public_' and ../../../../bgp:type='ibgp'";
                    type add-path-cap-type;
                    default "null";
                    description
                      "Enable Add-Path route advertisement to a peer.";
                  }
                  uses ip-prefix-filter-type;
                  uses as-path-filter-type;
                  uses rt-update-interval-type;
                  leaf nexthop-configure {
                    type nexthop-configuration-type;
                    description
                      "Both the next-hop-local mode and next-hop-invariable mode are available when the peer address family is the VPNv4/VPNV6/L2VPN AD address family. Only the next-hop-local mode is available when the peer address family is not VPNv4/VPNV6/L2VPN AD address family. In next-hop-local mode, you can configure a BGP speaker to set its IP address of as the next hop of the routes to be advertised to IBGP peers or IBGP peer groups. In next-hop-invariable mode, you can configure PEs in different ASs not to change the next hop of routes when the PEs advertise the routes to their EBGP peers and use the next hop addresses of IGP routes to advertise imported IGP routes to IBGP peers. By default, when a BGP speaker advertises routes to EBGP peers and imported IGP routes to IBGP peers, the BGP speaker changes the next hop to its interface address.";
                  }
                  uses preferred-value-type;
                  leaf add-path-number {
                    when "../../../../../../../../ni:name='_public_' and ../../../../bgp:type='ibgp'";
                    type uint8 {
                      range "2..64";
                    }
                    description
                      "Number of Add-Path routes that can be advertised to a peer.";
                  }
                  leaf substitute-as-enable {
                    when "../../../../bgp:type='ebgp'";
                    type boolean;
                    default "false";
                    description
                      "Enable/disable replace the AS number of a specified peer in the AS_Path attribute with the local AS number. On a PE where AS number replacement is enabled, if an AS number in the AS_Path attribute of a route is same as that of the CE to which the PE advertises the route, the PE replaces the AS number with its own AS number before advertising the route.";
                  }
                  leaf soo {
                    when "../../../../../../../../ni:name!='_public_'";
                    type string {
                      length "3..21";
                    }
                    description
                      "Configure the Site-of-Origin (SoO) extended community attribute. This attribute can be expressed in the following formats: X.X.X.X:number<0-65535>, number<0-65535>:number<0-4294967295>, or number<0-65535>.number<0-65535>:number<0-65535> or <65536-4294967295>:<0-65535>. 0:0 or 0.0:0 is not supported. 
                      Two CEs are in the same site and can advertise routes to each other, and they are connected to a VPN through PEs. If the local routes of a CE are advertised to the other CE over the VPN, a routing loop may occur. 
                      The SoO feature can prevent a route advertised by a site from being sent back to the site, preventing routing loops. After SoO is enabled and a PE receives a route from a CE, the specified SoO attribute will be added to the route. Before advertising the route to the other CE, the PE checks the SoO attribute. If the SoO attribute is the same as the locally configured SoO attribute, the PE does not advertise the route, preventing routing loops.";
                  }
                  leaf advertise-best-external {
                    when "../../../../../../../../ni:name='_public_' and ../../../../bgp:type='ibgp'";
                    type boolean;
                    must "../reflect-client='false' or ../advertise-best-external='false'";
                    must "../add-path-mode='null' or not(../add-path-mode) or ../advertise-best-external='false'";
                    must "not(../add-path-number and ../advertise-best-external='true')";
                    default "false";
                    description
                      "Enable/disable the device to advertise Best External routes to peers.";
                  }
                  leaf load-balancing-enable {
                    when "../../../../../../../../ni:name='_public_'";
                    type boolean;
                    default "false";
                    description
                      "Enable/disable a neighbour to participate in load balancing.";
                  }
                  choice load-balancing-ignore-as-type {
                    description
                      "Set load balancing as path type.";
                    case as-attribute {
                      description
                        "Ignore the as-path attribute.";
                      leaf load-balancing-as-path-ignore {
                        when "../load-balancing-enable='true'";
                        type empty;
                        description
                          "Configure BGP to ignore the AS_Path attribute when selecting the equal route. After as-path-neglect is selected, BGP does not compare the AS_Path length.";
                      }
                    }
                    case same-length-as-attribute {
                      description
                        "Ignore comparison of as-path attributes with the same length.";
                      leaf load-balancing-as-path-relax {
                        when "../load-balancing-enable='true'";
                        type empty;
                        description
                          "Configure BGP to ignore comparison of AS_Path attributes with the same length when selecting the equal route. After as-path-neglect is selected, BGP does not compare the AS_Path length.";
                      }
                    }
                  }
                  uses advertise-large-community-group-type;
                  uses route-limit-accept-type;
                  uses public-as-only-type;
                  container entropy-label-parameter {
                    when "../../../../../../../../ni:name='_public_'";
                    description
                      "Configure information about entropy label parameter in a peer group.";
                    uses group-entropy-label-type;
                  }
                }
                container ipv4-multicast {
                  when "../type='ipv4multi'";
                  description
                    "Configure IPv4 multicast options.";
                  uses default-route-advertise-type;
                  uses ip-prefix-filter-type;
                  uses as-path-filter-type;
                  leaf advertise-ext-community {
                    type boolean;
                    default "false";
                    description
                      "Enable/disable advertise the extended community attribute to a peer or peer group.";
                  }
                  leaf discard-ext-community {
                    type boolean;
                    default "false";
                    description
                      "Enable/disable discard the extended community attribute in the routing information about a specified peer.";
                  }
                  leaf allow-as-loop {
                    type uint32 {
                      range "1..10";
                    }
                    description
                      "Allow repetitive local AS numbers. By default, repetitive local AS numbers are not allowed.";
                  }
                  leaf nexthop-configure {
                    type nexthop-configuration-type;
                    must "../nexthop-configure='local'";
                    description
                      "Both the next-hop-local mode and next-hop-invariable mode are available when the peer address family is the VPNv4/VPNV6/L2VPN AD address family. Only the next-hop-local mode is available when the peer address family is not VPNv4/VPNV6/L2VPN AD address family. In next-hop-local mode, you can configure a BGP speaker to set its IP address of as the next hop of the routes to be advertised to IBGP peers or IBGP peer groups. In next-hop-invariable mode, you can configure PEs in different ASs not to change the next hop of routes when the PEs advertise the routes to their EBGP peers and use the next hop addresses of IGP routes to advertise imported IGP routes to IBGP peers. By default, when a BGP speaker advertises routes to EBGP peers and imported IGP routes to IBGP peers, the BGP speaker changes the next hop to its interface address.";
                  }
                  leaf advertise-community {
                    type boolean;
                    default "false";
                    description
                      "Enable/disable advertise the community attribute to a peer or a peer group.";
                  }
                  leaf keep-all-routes {
                    when "/bgp:bgp/bgp:base-process/bgp:keep-all-routes='false'";
                    type boolean;
                    default "false";
                    description
                      "Enable/disable saving all the updated information about BGP routes from a specified peer or peer group after a BGP connection is established, even though these BGP routes fail to match the routing policy on the ingress. By default, the updated information about BGP routes from a specified peer is saved only when the routes match the routing policy on the ingress. If a router supports route refreshing, this option is not required.";
                  }
                  choice import-policy-type {
                    description
                      "Set route policy or filter.";
                    case rtp-ref {
                      description
                        "Route policy.";
                      leaf import-policy {
                        type leafref {
                          path "/rtp:routing-policy/rtp:policy-definitions/rtp:policy-definition/rtp:name";
                        }
                        description
                          "Specify the filtering policy applied to the routes learned from a peer. By default, no such policy is specified.";
                      }
                    }
                  }
                  choice export-policy-type {
                    description
                      "Set route policy or filter.";
                    case rtp-ref {
                      description
                        "Route policy.";
                      leaf export-policy {
                        type leafref {
                          path "/rtp:routing-policy/rtp:policy-definitions/rtp:policy-definition/rtp:name";
                        }
                        description
                          "Specify the filtering policy applied to the routes to be advertised to a peer. By default, no such policy is specified.";
                      }
                    }
                  }
                  leaf reflect-client {
                    when "../../../../bgp:type='ibgp'";
                    type boolean;
                    default "false";
                    description
                      "Enable/disable the local device as a route reflector (RR) and a peer or peer group as its client. This configuration is applicable between IBGP peers only. The configurations of RRs and its clients in an address family are valid only in this address family. Therefore, it is recommended to configure RRs and its clients in the specified address family that is required.";
                  }
                  uses advertise-large-community-group-type;
                  uses rt-update-interval-type;
                  uses bgp:preferred-value-type;
                  uses route-limit-type;
                  uses public-as-only-type;
                }
              }
            }
          }
        }
        container peers {
          description
            "List of BGP peers.";
          list peer {
            key "address";
            description
              "Configure a single BGP peer.";
            leaf address {
              type inet:ip-address-no-zone;
              description
                "Connection address of a peer, which can be an IPv4 or IPv6 address.";
            }
            leaf remote-as {
              type as-number-validate;
              mandatory true;
              description
                "AS number of a peer, which must be selected or group name when creating, and which can be in either two-byte format or four-byte format:
                 The two-byte format is X. X is an integer ranging from 1 to 65535.
                 The four-byte format is X.Y and X. When the format is X.Y, X and Y are both integers, with the value of X ranging from 1 to 65535, and the value of Y ranging from 0 to 65535; when the format is X, X is an interger, with the value of X ranging from 1 to 4294967295.
                 The object cannot be modified.";
              ext:operation-exclude update {
                description "The node cannot be modified, when node is already configured.";
              }
            }
            leaf group-name {
              type leafref {
                path "../../../peer-groups/peer-group/name";
              }
              description
                "Specify the name of a peer group that BGP peers need to join. That must be selected group name or AS when creating, and the value is a string, spaces not supported. By default, BGP peers join no peer group. BGP peers distinguish the peer group type when joining a peer group. IBGP peers cannot join an EBGP peer group. BGP peers will be deleted when they leave a peer group. The object cannot be modified.";
              ext:operation-exclude update {
                description "The node cannot be modified, when the peer already belongs to a peer-group.";
              }
            }
            leaf local-if-name {
              type leafref {
                path "/ifm:ifm/ifm:interfaces/ifm:interface/ifm:name";
              }
              description
                "Name of a source interface that sends BGP packets. By default, the outbound interface of a BGP packet serves as the source interface of a BGP packet. To ensure that a router can send BGP packets when a physical interface fails, you can configure the source interface that sends BGP packets as a loopback interface. When using the loopback interface as the source interface, note the following points: 1. The address of the loopback interface of the BGP peer must be reachable. 2. For an EBGP connection, configure the maximum number of hops and allow EBGP peer relationships to be established in indirect mode.";
            }
            uses authentication-attr-type;
/*all product not support
            uses path-attr-map-type;
*/
            leaf description {
              type string {
                length "1..255";
                pattern '([^?]*)';
              }
              description
                "Description of a peer, which can be letters or digits. The description is a string, spaces supported. By default, no description is configured for a peer.";
            }
            leaf local-if-address {
              type inet:ip-address-no-zone;
              description
                "Name of a source interface that sends BGP packets. By default, the outbound interface of a BGP packet serves as the source interface of a BGP packet. To ensure that a router can send BGP packets when a physical interface fails, you can configure the source interface that sends BGP packets as a loopback interface. When using the loopback interface as the source interface, note the following points:
                1. The address of the loopback interface of the BGP peer must be reachable.
                 2. For an EBGP connection, configure the maximum number of hops and allow EBGP peer relationships to be established in indirect mode.";
            }
            leaf ebgp-max-hop {
              type uint32 {
                range "1..255";
              }
              must "not(../valid-ttl-hops) or (../valid-ttl-hops>=1 and ../valid-ttl-hops<=255 and ../ebgp-max-hop=1)";
              description
                "Maximum number of hops in an indirect EBGP connection. By default, EBGP connections can be established only between directly connected peers. The function must be configured on both ends. By default, value is determined by the neighbor type, the default value of EBGP is 1 and the default value of IBGP is 0.";
            }
            leaf tracking-enable {
              type boolean;
              default "false";
              description
                "Enable/disable peer tracking, After peer tracking is enabled, the device can fast detect the unreachability of a peer and reset the session.";
            }
            leaf tracking-delay-time {
              when "../tracking-enable='true'";
              type uint16;
              units "s";
              default "0";
              description
                "Specify the delay to reset the session.";
            }
            leaf conventional {
              type boolean;
              default "false";
              description
                "Enable/disable general router functions on peers. In conventional mode, not all the extended router functions, such as, route refreshing, GR, and multi-address family negotiation, are available. Therefore, the router of a new version can be compatible with the routers of earlier versions.";
            }
            leaf route-refresh {
              type boolean;
              default "true";
              description
                "Enable/disable BGP to advertise Refresh messages to peers.";
            }
            leaf four-byte-as {
              type boolean;
              default "true";
              description
                "Enable/disable BGP to advertise routes carrying 4-byte AS numbers to peers. After the 4-byte AS number function is disabled, Open packets will not carry 4-byte AS number capability flag, and peer ends will not know that local ends have the 4-byte AS number function. The 4-byte AS number function cannot be disabled from peers (peer groups) if a 4-byte AS number, fake AS number, or confederation ID is configured on a router and the AS number of a peer is 4-byte. If the 4-byte AS number function is disabled in such a situation, BGP sessions may fail to be established, and route transmission may be affected.";
            }
            leaf ignore {
              type boolean;
              default "false";
              description
                "Enable/disable the function to tear down sessions between peers and clear all related routing information.";
            }
            leaf valid-ttl-hops {
              type uint16 {
                range "1..255";
              }
              must "not(../ebgp-max-hop and ../ebgp-max-hop>1 and ../ebgp-max-hop<=255)";
              description
                "Enable GTSM on a peer or peer group. The valid-TTL-Value parameter is used to specify the number of TTL hops to be detected. If the value is configured as hops, the valid TTL range of the detected packet is [255-hops+1, 255].";
            }
            leaf connect-mode {
              type connect-mode;
              default "null";
              description
                "The value can be Connect-only, Listen-only, or Both. If the value is Connect-only, the specified peer or peer group only initiatively sends connection requests, instead of listening to connection requests. If the value is Listen-only, the specified peer or peer group only listens to connection requests, instead of initiatively sending connection requests. If the value is Both, the specified peer or peer group not only initiatively sends connection requests, but also listens to connection requests. The default value is Both.";
            }
            leaf log-change {
              type boolean;
              default "true";
              description
                "Enable/disable BGP to record the session status and events of the specified peer or peer group.";
            }
            leaf path-mtu-auto-discovery {
              type boolean;
              default "false";
              description
                "Enable/disable path mtu auto discovery.";
            }
            leaf local-ifnet-disable {
              when "../../../../../ni:name='_public_'";
              type boolean;
              description
                "Enable/disable MPLS local IFNET tunnel creation on a BGP IPv4 peer. By default, MPLS local IFNET tunnels can be created on an EBGP peer,but such tunnels cannot be created on an IBGP peer.";
              ext:dynamic-default;
            }
            leaf check-first-as {
              type peer-cap-config-state;
              default "default";
              description
                "Check the first AS in the AS_Path of the update messages from EBGP peers.";
            }
            leaf egress-engineer {
              when "../../../../../ni:name='_public_'";
              type epe-state;
              default "default";
              description
                "BGP Egress Peer Engineering (BGP-EPE) is enable or disable. The default value is default (The function is disable, If the neighbour joins the group, the function is Inheritance group).";
            }
            leaf tcp-mss {
              type uint16 {
                range "176..4096";
              }
              description
                "Maximum TCP MSS value used for TCP connection establishment for a peer.";
            }
            leaf memory-priority {
              type peer-memory-priority;
              default "default";
              description
                "Set a priority that determines the disconnection order of a BGP peer relationship if memory overload occurs.";
            }
            leaf memory-priority-capability {
              type memory-priority;
              config false;
              description
                "Priority that is used to determine the disconnection order of a BGP peer relationship if memory overload occurs.";
            }
            uses fake-as-type;
            uses peer-timer-para-type;
            container bfd-parameter {
              description
                "Configure BFD.";
              leaf block {
                type boolean;
                must "not(../block='true' and ../enable='true')";
                default "false";
                description
                  "Enable/disable preventing a BGP peer from inheriting the BFD configuration of the BGP peer group.";
              }
              leaf enable {
                type boolean;
                must "not(../block='true' and ../enable='true')";
                default "false";
                description
                  "Enable/disable BFD.";
              }
              choice mode-type {
                description
                  "Set bfd mode.";
                case single {
                  description
                    "Single hop mode.";
                  leaf single-hop {
                    when "../enable='true'";
                    type empty;
                    description
                      "The single hop mode is preferred during the BFD session establishment between IBGP peers.";
                  }
                  leaf compatible {
                    when "../enable='true'";
                    type empty;
                    description
                      "Compatible.";
                  }
                }
                case link {
                  description
                    "The per-link-echo mode.";
                  leaf per-link-echo {
                    when "../enable='true'";
                    type empty;
                    description
                      "The per-link one-arm-echo mode is preferred during the BFD session establishment between IBGP peers.";
                  }
                }
              }
              uses bfd-detect-parameter-type;
            }
            container egress-engineer-parameter {
              when "../egress-engineer='enable'";
              description
                "Configure BGP peer egress engineering information.";
              leaf static-label {
                type uint32;
                description
                  "The static label for BGP EPE.";
              }
              leaf label-pop {
                when "../static-label";
                type boolean;
                must "not(../relate-bfd='true' and ../label-pop='true')";
                default "false";
                description
                  "Enable/disable the BGP-EPE label popping function.";
              }
              leaf relate-bfd {
                type boolean;
                must "not(../relate-bfd='true' and ../label-pop='true')";
              default "false";
                description
                  "Enable/disable association between the BGP-EPE label and BFD status.";
              }
              leaf peer-set-name {
                type leafref {
                path "../../../../bgp:egress-engineer-peer-sets/bgp:egress-engineer-peer-set/bgp:peer-set-name";
                }
                description
                  "Add peer to peer set.";
              }
            }
            container graceful-restart {
              description
                "Configure graceful restart.";
              uses peer-graceful-restart-type;
              leaf peer-reset {
                type peer-comm-config-type;
                default "default";
                description
                  "Enable/disable reseting BGP peer graceful.";
              }
              leaf effect-peer-reset {
                type boolean;
                config false;
                description
                  "Whether enable/disable reseting BGP peer graceful.";
              }
            }
            container local-graceful-restart {
              description
                "Configure local graceful restart.";
              uses peer-graceful-restart-type;
            }
            container afs {
              description
                "List of peers in a specified address family.";
              list af {
                key "type";
                description
                  "Configure peer in a specified address family.";
                leaf type {
                  type bgp:af-type;
                  must "../../../../../afs/af[type = current()]";
                  description
                    "Specify the address family type to set the peer enable.";
                }
                container ipv4-unicast {
                  when "../type='ipv4uni'";
                  description
                    "Configure IPv4 unicast options.";
                  leaf group-name {
                    type leafref {
                      path "../../../../../../peer-groups/peer-group/name";
                    }
                    must "../../../../../../peer-groups/peer-group[name = current()]/afs/af[type = 'ipv4uni']";
                    description
                      "Configure a name for a peer group. After a peer is deleted from the peer group, the peer is disabled from the address family. The object cannot be modified.";
                    ext:operation-exclude update {
                      description "The node cannot be modified, when the peer already belongs to a peer-group.";
                    }
                  }
                  leaf advertise-community {
                    type boolean;
                    default "false";
                    description
                      "Enable/disable advertise the community attribute to a peer or a peer group.";
                  }
                  leaf reflect-client {
                    type boolean;
                    default "false";
                    description
                      "Enable/disable the local device as a route reflector (RR) and a peer or peer group as its client. This configuration is applicable between IBGP peers only. The configurations of RRs and its clients in an address family are valid only in this address family. Therefore, it is recommended to configure RRs and its clients in the specified address family that is required.";
                  }
                  leaf orf-type {
                    when "../../../../../../../../ni:name='_public_'";
                    type bgp:bgp-orf-type;
                    must "(../orf-mode='null' and ../orf-type='null') or (../orf-mode!='null' and ../orf-type!='null')";
                    default "null";
                    description
                      "ORF Type.";
                  }
                  leaf orf-mode {
                    when "../../../../../../../../ni:name='_public_'";
                    type bgp:bgp-orf-mode-type;
                    must "(../orf-mode='null' and ../orf-type='null') or (../orf-mode!='null' and ../orf-type!='null')";
                    default "null";
                    description
                      "Configure an outbound route filtering (ORF) mode, which can be Receive, Send, or Both, and the default ORF mode is Both.";
                  }
                  leaf label-route-capability {
                    type boolean;
                    default "false";
                    description
                      "Enable/disable a device to exchange labeled routes.";
                  }
                  leaf check-tunnel-reachable {
                    when "../label-route-capability='true'";
                    type boolean;
                    default "false";
                    description
                      "Enable/disable tunnel reachability check.";
                  }
                  leaf check-withdraw-type {
                    when "../label-route-capability='true'";
                    type boolean;
                    default "true";
                    description
                      "Enable/disable withdraw type check.";
                  }
                  leaf nexthop-configure {
                    type nexthop-configuration-type;
                    description
                      "Both the next-hop-local mode and next-hop-invariable mode are available when the peer address family is the VPNv4/VPNV6/L2VPN AD address family. Only the next-hop-local mode is available when the peer address family is not VPNv4/VPNV6/L2VPN AD address family. In next-hop-local mode, you can configure a BGP speaker to set its IP address of as the next hop of the routes to be advertised to IBGP peers or IBGP peer groups. In next-hop-invariable mode, you can configure PEs in different ASs not to change the next hop of routes when the PEs advertise the routes to their EBGP peers and use the next hop addresses of IGP routes to advertise imported IGP routes to IBGP peers. By default, when a BGP speaker advertises routes to EBGP peers and imported IGP routes to IBGP peers, the BGP speaker changes the next hop to its interface address.";
                  }
                  choice import-policy-type {
                    description
                      "Set route policy or filter.";
                    case rtp-ref {
                      description
                        "Route policy.";
                      leaf import-policy {
                        type leafref {
                          path "/rtp:routing-policy/rtp:policy-definitions/rtp:policy-definition/rtp:name";
                        }
                        description
                          "Specify the filtering policy applied to the routes learned from a peer. By default, no such policy is specified.";
                      }
                    }
                    case xpl-ref {
                      description
                        "Route filter.";
                      container import-filter {
                        description
                          "Configure an import route-filter to filter the routes received from peers. By default, no route-filter is specified to filter the routes imported from peers.";
                        leaf name {
                          type leafref {
                            path "/xpl:xpl/xpl:route-filters/xpl:route-filter/xpl:name";
                          }
                          description
                            "Specify an import route-filter name.";
                        }
                        leaf parameter {
                          when "../name";
                          type string {
                            length "1..1609";
                          }
                          description
                            "Specify an import route-filter parameter.";
                        }
                      }
                    }
                  }
                  choice export-policy-type {
                    description
                      "Set route policy or filter.";
                    case rtp-ref {
                      description
                        "Route policy.";
                      leaf export-policy {
                        type leafref {
                          path "/rtp:routing-policy/rtp:policy-definitions/rtp:policy-definition/rtp:name";
                        }
                        description
                          "Specify the filtering policy applied to the routes to be advertised to a peer. By default, no such policy is specified.";
                      }
                    }
                    case xpl-ref {
                      description
                        "Route filter.";
                      container export-filter {
                        description
                          "Configure an export route-filter to filter the routes to be advertised to peers. By default, no route-filter is specified to filter the routes to be advertised to peers.";
                        leaf name {
                          type leafref {
                            path "/xpl:xpl/xpl:route-filters/xpl:route-filter/xpl:name";
                          }
                          description
                            "Specify an export route-filter name.";
                        }
                        leaf parameter {
                          when "../name";
                          type string {
                            length "1..1609";
                          }
                          description
                            "Specify an export route-filter parameter.";
                        }
                      }
                    }
                  }
                  leaf advertise-ext-community {
                    type boolean;
                    default "false";
                    description
                      "Enable/disable advertise the extended community attribute to a peer or peer group.";
                  }
                  leaf discard-ext-community {
                    type boolean;
                    default "false";
                    description
                      "Enable/disable discard the extended community attribute in the routing information about a specified peer.";
                  }
                  leaf allow-as-loop {
                    type uint32 {
                      range "1..10";
                    }
                    description
                      "Allow repetitive local AS numbers. By default, repetitive local AS numbers are not allowed.";
                  }
                  leaf aigp {
                    when "../../../../../../../../ni:name='_public_'";
                    type boolean;
                    default "false";
                    description
                      "Enable/disable route with AIGP attribute advertisement to or from a peer.";
                  }
                  uses default-route-advertise-type;
                  leaf default-route-match-mode {
                    when "../default-route-advertise='true'";
                    type cra-match-mode;
                    default "null";
                    description
                      "Configure the matching mode of default route advertisement, which can be disabling of route advertisement conditions, enabling of all route advertisement conditions, and enabling of part route advertisement conditions. Enabling of all route advertisement conditions indicates that a default route can be advertised only when it matches all the conditions. Enabling of part route advertisement conditions indicates that a default route can be advertised only when it matches one condition.";
                  }
                  leaf add-path-mode {
                    when "../../../../../../../../ni:name='_public_'";
                    type add-path-cap-type;
                    default "null";
                    description
                      "Enable add-path route advertisement to a peer.";
                  }
                  uses ip-prefix-filter-type;
                  uses as-path-filter-type;
                  uses rt-update-interval-type;
                  uses preferred-value-type;
                  leaf add-path-number {
                    when "../../../../../../../../ni:name='_public_'";
                    type uint8 {
                      range "2..64";
                    }
                    description
                      "Number of add-path routes that can be advertised to a peer.";
                  }
                  leaf substitute-as-enable {
                    type boolean;
                    default "false";
                    description
                      "Enable/disable replace the AS number of a specified peer in the AS_Path attribute with the local AS number. On a PE where AS number replacement is enabled, if an AS number in the AS_Path attribute of a route is same as that of the CE to which the PE advertises the route, the PE replaces the AS number with its own AS number before advertising the route.";
                  }
                  leaf soo {
                    when "../../../../../../../../ni:name!='_public_'";
                    type string {
                      length "3..21";
                    }
                    description
                      "Configure the Site-of-Origin (SoO) extended community attribute. This attribute can be expressed in the following formats: X.X.X.X:number<0-65535>, number<0-65535>:number<0-4294967295>, or number<0-65535>.number<0-65535>:number<0-65535> or <65536-4294967295>:<0-65535>. 0:0 or 0.0:0 is not supported. 
                      Two CEs are in the same site and can advertise routes to each other, and they are connected to a VPN through PEs. If the local routes of a CE are advertised to the other CE over the VPN, a routing loop may occur. 
                      The SoO feature can prevent a route advertised by a site from being sent back to the site, preventing routing loops. After SoO is enabled and a PE receives a route from a CE, the specified SoO attribute will be added to the route. Before advertising the route to the other CE, the PE checks the SoO attribute. If the SoO attribute is the same as the locally configured SoO attribute, the PE does not advertise the route, preventing routing loops.";
                  }
                  leaf keep-all-routes {
                    when "/bgp:bgp/bgp:base-process/bgp:keep-all-routes='false'";
                    type boolean;
                    default "false";
                    description
                      "Enable/disable saving all the updated information about BGP routes from a specified peer or peer group after a BGP connection is established, even though these BGP routes fail to match the routing policy on the ingress. By default, the updated information about BGP routes from a specified peer is saved only when the routes match the routing policy on the ingress. If a router supports route refreshing, this option is not required.";
                  }
                  leaf exp-mode {
                    when "../../../../../../../../ni:name='_public_'";
                    type exp-mode-type;
                    default "null";
                    description
                      "Specify the ASs in which a BGP label can inherit the QoS priority carried in the outer label of public tunnel in the Core AS and the ASs in which the priorities of BGP LSPs must be restored before the LSPs are advertised to a non-core AS.";
                  }
                  leaf advertise-best-external {
                    when "../../../../../../../../ni:name='_public_'";
                    type boolean;
                    must "../reflect-client='false' or ../advertise-best-external='false'";
                    must "../add-path-mode='null' or not(../add-path-mode) or ../advertise-best-external='false'";
                    must "not(../add-path-number and ../advertise-best-external='true')";
                    default "false";
                    description
                      "Enable/disable the device to advertise Best External routes to peers.";
                  }
                  leaf load-balancing-enable {
                    type boolean;
                    default "false";
                    description
                      "Enable/disable a neighbour to participate in load balancing.";
                  }
                  choice load-balancing-ignore-as-type {
                    description
                      "Set load balancing as path type.";
                    case as-attribute {
                      description
                        "Ignore the as-path attribute.";
                      leaf load-balancing-as-path-ignore {
                        when "../load-balancing-enable='true'";
                        type empty;
                        description
                          "Configure BGP to ignore the AS_Path attribute when selecting the equal route. After as-path-neglect is selected, BGP does not compare the AS_Path length.";
                      }
                    }
                    case same-length-as-attribute {
                      description
                        "Ignore comparison of as-path attributes with the same length.";
                      leaf load-balancing-as-path-relax {
                        when "../load-balancing-enable='true'";
                        type empty;
                        description
                          "Configure BGP to ignore comparison of AS_Path attributes with the same length when selecting the equal route. After as-path-neglect is selected, BGP does not compare the AS_Path length.";
                      }
                    }
                  }
                  leaf prefix-sid {
                    when "../../../../../../../../ni:name='_public_'";
                    type bgp:peer-comm-config-type;
                    default "default";
                    description
                  	"Enable/disable a device to exchange IPv4 prefix SIDs with a specified IPv6 peer.";
                  }
                  leaf prefix-sid-state {
                    when "../../../../../../../../ni:name='_public_'";
                    type boolean;
                    default "false";
                    config false;
                    description
                  	"Whether the prefix-sid to a peer is enabled.";
                  }
                  uses advertise-large-community-type;
                  uses ipv4-default-route-match-conditions-type;
                  uses route-limit-accept-type;
                  uses public-as-only-type;
                  container entropy-label-parameter {
                    when "../../../../../../../../ni:name='_public_' and ../label-route-capability='true'";
                    description
                      "Configure information about entropy label parameter configuration in a peer.";
                    uses peer-entropy-label-type;
                  }
                  uses path-attr-map-type;
                }
                container ipv6-unicast {
                  when "../type = 'ipv6uni'";
                  description
                    "Configure IPv6 unicast options.";
                  leaf group-name {
                    type leafref {
                      path "../../../../../../peer-groups/peer-group/name";
                    }
                    must "../../../../../../peer-groups/peer-group[name = current()]/afs/af[type = 'ipv6uni']";
                    description
                      "Configure a name for a peer group. After a peer is deleted from the peer group, the peer is disabled from the address family. The object cannot be modified.";
                    ext:operation-exclude update {
                      description "The node cannot be modified, when the peer already belongs to a peer-group.";
                    }
                  }
                  leaf advertise-community {
                    type boolean;
                    default "false";
                    description
                      "Enable/disable advertise the community attribute to a peer or a peer group.";
                  }
                  leaf reflect-client {
                    type boolean;
                    default "false";
                    description
                      "Enable/disable the local device as a route reflector (RR) and a peer or peer group as its client. This configuration is applicable between IBGP peers only. The configurations of RRs and its clients in an address family are valid only in this address family. Therefore, it is recommended to configure RRs and its clients in the specified address family that is required.";
                  }
                  leaf label-route-capability {
                    type boolean;
                    default "false";
                    description
                      "Enable/disable a device to exchange labeled routes.";
                  }
                  leaf nexthop-configure {
                    type nexthop-configuration-type;
                    must "(not(contains(../../../../address,':')) and ../nexthop-configure='local') or contains(../../../../address,':')";
                    description
                      "Both the next-hop-local mode and next-hop-invariable mode are available when the peer address family is the VPNv4/VPNV6/L2VPN AD address family. Only the next-hop-local mode is available when the peer address family is not VPNv4/VPNV6/L2VPN AD address family. In next-hop-local mode, you can configure a BGP speaker to set its IP address of as the next hop of the routes to be advertised to IBGP peers or IBGP peer groups. In next-hop-invariable mode, you can configure PEs in different ASs not to change the next hop of routes when the PEs advertise the routes to their EBGP peers and use the next hop addresses of IGP routes to advertise imported IGP routes to IBGP peers. By default, when a BGP speaker advertises routes to EBGP peers and imported IGP routes to IBGP peers, the BGP speaker changes the next hop to its interface address.";
                  }
                  choice import-policy-type {
                    description
                      "Set route policy or filter.";
                    case rtp-ref {
                      description
                        "Route policy.";
                      leaf import-policy {
                        type leafref {
                          path "/rtp:routing-policy/rtp:policy-definitions/rtp:policy-definition/rtp:name";
                        }
                        description
                          "Specify the filtering policy applied to the routes learned from a peer. By default, no such policy is specified.";
                      }
                    }
                  }
                  choice export-policy-type {
                    description
                      "Set route policy or filter.";
                    case rtp-ref {
                      description
                        "Route policy.";
                      leaf export-policy {
                        type leafref {
                          path "/rtp:routing-policy/rtp:policy-definitions/rtp:policy-definition/rtp:name";
                        }
                        description
                          "Specify the filtering policy applied to the routes to be advertised to a peer. By default, no such policy is specified.";
                      }
                    }
                  }
                  leaf advertise-ext-community {
                    type boolean;
                    default "false";
                    description
                      "Enable/disable advertise the extended community attribute to a peer or peer group.";
                  }
                  leaf discard-ext-community {
                    type boolean;
                    default "false";
                    description
                      "Enable/disable discard the extended community attribute in the routing information about a specified peer.";
                  }
                  leaf allow-as-loop {
                    type uint32 {
                      range "1..10";
                    }
                    description
                      "Allow repetitive local AS numbers. By default, repetitive local AS numbers are not allowed.";
                  }
                  leaf aigp {
                    when "../../../../../../../../ni:name='_public_'";
                    type boolean;
                    default "false";
                    description
                      "Enable/disable route with AIGP attribute advertisement to or from a peer.";
                  }
                  uses default-route-advertise-type;
                  leaf default-route-match-mode {
                    when "../default-route-advertise='true'";
                    type cra-match-mode;
                    default "null";
                    description
                      "Configure the matching mode of default route advertisement, which can be disabling of route advertisement conditions, enabling of all route advertisement conditions, and enabling of part route advertisement conditions. Enabling of all route advertisement conditions indicates that a default route can be advertised only when it matches all the conditions. Enabling of part route advertisement conditions indicates that a default route can be advertised only when it matches one condition.";
                  }
                  leaf add-path-mode {
                    when "../../../../../../../../ni:name='_public_'";
                    type add-path-cap-type;
                    default "null";
                    description
                      "Enable Add-Path route advertisement to a peer.";
                  }
                  uses ipv6-prefix-filter-type;
                  uses as-path-filter-type;
                  uses rt-update-interval-type;
                  uses preferred-value-type;
                  leaf add-path-number {
                    when "../../../../../../../../ni:name='_public_'";
                    type uint8 {
                      range "2..64";
                    }
                    description
                      "Number of Add-Path routes that can be advertised to a peer.";
                  }
                  leaf substitute-as-enable {
                    type boolean;
                    default "false";
                    description
                      "Enable/disable replace the AS number of a specified peer in the AS_Path attribute with the local AS number. On a PE where AS number replacement is enabled, if an AS number in the AS_Path attribute of a route is same as that of the CE to which the PE advertises the route, the PE replaces the AS number with its own AS number before advertising the route.";
                  }
                  leaf soo {
                    when "../../../../../../../../ni:name!='_public_'";
                    type string {
                      length "3..21";
                    }
                    description
                      "Configure the Site-of-Origin (SoO) extended community attribute. This attribute can be expressed in the following formats: X.X.X.X:number<0-65535>, number<0-65535>:number<0-4294967295>, or number<0-65535>.number<0-65535>:number<0-65535> or <65536-4294967295>:<0-65535>. 0:0 or 0.0:0 is not supported. 
                      Two CEs are in the same site and can advertise routes to each other, and they are connected to a VPN through PEs. If the local routes of a CE are advertised to the other CE over the VPN, a routing loop may occur. 
                      The SoO feature can prevent a route advertised by a site from being sent back to the site, preventing routing loops. After SoO is enabled and a PE receives a route from a CE, the specified SoO attribute will be added to the route. Before advertising the route to the other CE, the PE checks the SoO attribute. If the SoO attribute is the same as the locally configured SoO attribute, the PE does not advertise the route, preventing routing loops.";
                  }
                  leaf keep-all-routes {
                    when "/bgp:bgp/bgp:base-process/bgp:keep-all-routes='false'";
                    type boolean;
                    default "false";
                    description
                      "Enable/disable saving all the updated information about BGP routes from a specified peer or peer group after a BGP connection is established, even though these BGP routes fail to match the routing policy on the ingress. By default, the updated information about BGP routes from a specified peer is saved only when the routes match the routing policy on the ingress. If a router supports route refreshing, this option is not required.";
                  }
                  leaf advertise-best-external {
                    when "../../../../../../../../ni:name='_public_'";
                    type boolean;
                    must "../reflect-client='false' or ../advertise-best-external='false'";
                    must "../add-path-mode='null' or not(../add-path-mode) or ../advertise-best-external='false'";
                    must "not(../add-path-number and ../advertise-best-external='true')";
                    default "false";
                    description
                      "Enable/disable the device to advertise Best External routes to peers.";
                  }
                  leaf load-balancing-enable {
                    type boolean;
                    default "false";
                    description
                      "Enable/disable a neighbour to participate in load balancing.";
                  }
                  choice load-balancing-ignore-as-type {
                    description
                      "Set load balancing as path type.";
                    case as-attribute {
                      description
                        "Ignore the as-path attribute.";
                      leaf load-balancing-as-path-ignore {
                        when "../load-balancing-enable='true'";
                        type empty;
                        description
                          "Configure BGP to ignore the AS_Path attribute when selecting the equal route. After as-path-neglect is selected, BGP does not compare the AS_Path length.";
                      }
                    }
                    case same-length-as-attribute {
                      description
                        "Ignore comparison of as-path attributes with the same length.";
                      leaf load-balancing-as-path-relax {
                        when "../load-balancing-enable='true'";
                        type empty;
                        description
                          "Configure BGP to ignore comparison of AS_Path attributes with the same length when selecting the equal route. After as-path-neglect is selected, BGP does not compare the AS_Path length.";
                      }
                    }
                  }
                  leaf tunnel-policy {
                    when "../../../../../../../../ni:name='_public_'";
                    type leafref {
                      path "/tnlm:tunnel-management/tnlm:tunnel-policys/tnlm:tunnel-policy/tnlm:name";
                    }
                    description
                      "Apply a tunnel policy for a 6PE peer. By default, no tunnel policy is configured.";
                  }
                  leaf prefix-sid {
                    when "../../../../../../../../ni:name='_public_'";
                    type bgp:peer-comm-config-type;
                    default "default";
                    description
                  	"Enable/disable a device to exchange prefix SIDs with a specified IPv6 peer.";
                  }
                  leaf prefix-sid-state {
                    when "../../../../../../../../ni:name='_public_'";
                    type boolean;
                    default "false";
                    config false;
                    description
                  	"Whether the prefix-sid to a peer is enabled.";
                  }
                  uses advertise-large-community-type;
                  uses ipv6-default-route-match-conditions-type;
                  uses route-limit-accept-type;
                  uses public-as-only-type;
                  uses path-attr-map-type;
                }
                container ipv4-vpn {
                  when "../type = 'ipv4vpn'";
                  description
                    "Configure IPv4 VPNv4 options.";
                  leaf group-name {
                    type leafref {
                      path "../../../../../../peer-groups/peer-group/name";
                    }
                    must "../../../../../../peer-groups/peer-group[name = current()]/afs/af[type = 'ipv4vpn']";
                    description
                      "Configure a name for a peer group. After a peer is deleted from the peer group, the peer is disabled from the address family. The object cannot be modified.";
                    ext:operation-exclude update {
                      description "The node cannot be modified, when the peer already belongs to a peer-group.";
                    }
                  }
                  leaf advertise-community {
                    type boolean;
                    default "false";
                    description
                      "Enable/disable advertise the community attribute to a peer or a peer group.";
                  }
                  leaf reflect-client {
                    type boolean;
                    default "false";
                    description
                      "Enable/disable the local device as a route reflector (RR) and a peer or peer group as its client. This configuration is applicable between IBGP peers only. The configurations of RRs and its clients in an address family are valid only in this address family. Therefore, it is recommended to configure RRs and its clients in the specified address family that is required.";
                  }
                  leaf nexthop-configure {
                    type nexthop-configuration-type;
                    description
                      "Both the next-hop-local mode and next-hop-invariable mode are available when the peer address family is the VPNv4/VPNV6/L2VPN AD address family. Only the next-hop-local mode is available when the peer address family is not VPNv4/VPNV6/L2VPN AD address family. In next-hop-local mode, you can configure a BGP speaker to set its IP address of as the next hop of the routes to be advertised to IBGP peers or IBGP peer groups. In next-hop-invariable mode, you can configure PEs in different ASs not to change the next hop of routes when the PEs advertise the routes to their EBGP peers and use the next hop addresses of IGP routes to advertise imported IGP routes to IBGP peers. By default, when a BGP speaker advertises routes to EBGP peers and imported IGP routes to IBGP peers, the BGP speaker changes the next hop to its interface address.";
                  }
                  choice import-policy-type {
                    description
                      "Set route policy or filter.";
                    case rtp-ref {
                      description
                        "Route policy.";
                      leaf import-policy {
                        type leafref {
                          path "/rtp:routing-policy/rtp:policy-definitions/rtp:policy-definition/rtp:name";
                        }
                        description
                          "Specify the filtering policy applied to the routes learned from a peer. By default, no such policy is specified.";
                      }
                    }
                  }
                  choice export-policy-type {
                    description
                      "Set route policy or filter.";
                    case rtp-ref {
                      description
                        "Route policy.";
                      leaf export-policy {
                        type leafref {
                          path "/rtp:routing-policy/rtp:policy-definitions/rtp:policy-definition/rtp:name";
                        }
                        description
                          "Specify the filtering policy applied to the routes to be advertised to a peer. By default, no such policy is specified.";
                      }
                    }
                  }
                  leaf allow-as-loop {
                    type uint32 {
                      range "1..10";
                    }
                    description
                      "Allow repetitive local AS numbers. By default, repetitive local AS numbers are not allowed.";
                  }
                  leaf aigp {
                    type boolean;
                    default "false";
                    description
                      "Enable/disable route with AIGP attribute advertisement to or from a peer.";
                  }
                  leaf add-path-mode {
                    type add-path-cap-type;
                    default "null";
                    description
                      "Enable Add-Path route advertisement to a peer.";
                  }
                  uses ip-prefix-filter-type;
                  leaf reoriginate-route-enable {
                    type boolean;
                    default "false";
                    description
                      "Enable/disable route regeneration.";
                  }
                  leaf reoriginate-ip-enable {
                    type boolean;
                    default "false";
                    description
                      "Enable/disable IP route regeneration and advertisement.";
                  }
                  leaf reoriginate-mac-ip-enable {
                    type boolean;
                    default "false";
                    description
                      "Enable/disable MAC-IP route regeneration and advertisement.";
                  }
                  leaf reoriginate-vpnv4-route-enable {
                    type boolean;
                    default "false";
                    description
                       "Enable/disable VPNv4 route regeneration and advertisement.";
                  }
                  uses as-path-filter-type;
                  uses rt-update-interval-type;
                  uses preferred-value-type;
                  leaf add-path-number {
                    type uint8 {
                      range "2..64";
                    }
                    description
                      "Number of add-path routes that can be advertised to a peer.";
                  }
                  leaf upe {
                    type boolean;
                    default "false";
                    description
                      "Enable/disable the peer as an underlayer PE (UPE).";
                  }
                  leaf high-priority {
                    type peer-enable-config-type;
                    default "default";
                    description
                       "Enable vpn-router high priority.";
                  }
                  leaf prefix-sid {
                    type bgp:peer-enable-config-type;
                    default "default";
                    description
                      "Specify a SID mode relay for peer.";
                  }
                  leaf advertise-best-external {
                    type boolean;
                    must "../reflect-client='false' or ../advertise-best-external='false'";
                    must "../add-path-mode='null' or not(../add-path-mode) or ../advertise-best-external='false'";
                    must "not(../add-path-number and ../advertise-best-external='true')";
                    default "false";
                    description
                      "Enable/disable the device to advertise Best External routes to peers.";
                  }
                  uses advertise-large-community-type;
                  leaf keep-all-routes {
                    when "/bgp:bgp/bgp:base-process/bgp:keep-all-routes='false'";
                    type boolean;
                    default "false";
                    description
                      "Enable/disable saving all the updated information about BGP routes from a specified peer or peer group after a BGP connection is established, even though these BGP routes fail to match the routing policy on the ingress. By default, the updated information about BGP routes from a specified peer is saved only when the routes match the routing policy on the ingress. If a router supports route refreshing, this option is not required.";
                  }
                  container default-route-originates {
                    description
                      "Configure advertised default VPNv4 routes.";
                    uses default-route-originate-type;
                  }
                  uses route-limit-type;
                  uses public-as-only-type;
                  uses path-attr-map-type;
                }
                container ipv6-vpn {
                  when "../type = 'ipv6vpn'";
                  description
                    "Configure IPv6 vpn options.";
                  leaf group-name {
                    type leafref {
                      path "../../../../../../peer-groups/peer-group/name";
                    }
                    must "../../../../../../peer-groups/peer-group[name = current()]/afs/af[type = 'ipv6vpn']";
                    description
                      "Configure a name for a peer group. After a peer is deleted from the peer group, the peer is disabled from the address family. The object cannot be modified.";
                    ext:operation-exclude update {
                      description "The node cannot be modified, when the peer already belongs to a peer-group.";
                    }
                  }
                  leaf advertise-community {
                    type boolean;
                    default "false";
                    description
                      "Enable/disable advertise the community attribute to a peer or a peer group.";
                  }
                  leaf reflect-client {
                    type boolean;
                    default "false";
                    description
                      "Enable/disable the local device as a route reflector (RR) and a peer or peer group as its client. This configuration is applicable between IBGP peers only. The configurations of RRs and its clients in an address family are valid only in this address family. Therefore, it is recommended to configure RRs and its clients in the specified address family that is required.";
                  }
                  leaf nexthop-configure {
                    type nexthop-configuration-type;
                    description
                      "Both the next-hop-local mode and next-hop-invariable mode are available when the peer address family is the VPNv4/VPNV6/L2VPN AD address family. Only the next-hop-local mode is available when the peer address family is not VPNv4/VPNV6/L2VPN AD address family. In next-hop-local mode, you can configure a BGP speaker to set its IP address of as the next hop of the routes to be advertised to IBGP peers or IBGP peer groups. In next-hop-invariable mode, you can configure PEs in different ASs not to change the next hop of routes when the PEs advertise the routes to their EBGP peers and use the next hop addresses of IGP routes to advertise imported IGP routes to IBGP peers. By default, when a BGP speaker advertises routes to EBGP peers and imported IGP routes to IBGP peers, the BGP speaker changes the next hop to its interface address.";
                  }
                  choice import-policy-type {
                    description
                      "Set route policy or filter.";
                    case rtp-ref {
                      description
                        "Route policy.";
                      leaf import-policy {
                        type leafref {
                          path "/rtp:routing-policy/rtp:policy-definitions/rtp:policy-definition/rtp:name";
                        }
                        description
                          "Specify the filtering policy applied to the routes learned from a peer. By default, no such policy is specified.";
                      }
                    }
                  }
                  choice export-policy-type {
                    description
                      "Set route policy or filter.";
                    case rtp-ref {
                      description
                        "Route policy.";
                      leaf export-policy {
                        type leafref {
                          path "/rtp:routing-policy/rtp:policy-definitions/rtp:policy-definition/rtp:name";
                        }
                        description
                          "Specify the filtering policy applied to the routes to be advertised to a peer. By default, no such policy is specified.";
                      }
                    }
                  }
                  leaf allow-as-loop {
                    type uint32 {
                      range "1..10";
                    }
                    description
                      "Allow repetitive local AS numbers. By default, repetitive local AS numbers are not allowed.";
                  }
                  leaf aigp {
                    type boolean;
                    default "false";
                    description
                      "Enable/disable route with AIGP attribute advertisement to or from a peer.";
                  }
                  leaf add-path-mode {
                    type add-path-cap-type;
                    default "null";
                    description
                      "Enable Add-Path route advertisement to a peer.";
                  }
                  uses ipv6-prefix-filter-type;
                  leaf reoriginate-route-enable {
                    type boolean;
                    default "false";
                    description
                      "Enable/disable route regeneration.";
                  }
                  leaf reoriginate-ipv6-enable {
                    type boolean;
                    default "false";
                    description
                      "Enable/disable IP route regeneration and advertisement.";
                  }
                  leaf reoriginate-mac-ipv6-enable {
                    type boolean;
                    default "false";
                    description
                      "Enable/disable MAC-IP route regeneration and advertisement.";
                  }
                  uses as-path-filter-type;
                  uses rt-update-interval-type;
                  uses preferred-value-type;
                  leaf add-path-number {
                    type uint8 {
                      range "2..64";
                    }
                    description
                      "Number of Add-Path routes that can be advertised to a peer.";
                  }
                  leaf advertise-best-external {
                    type boolean;
                    must "../reflect-client='false' or ../advertise-best-external='false'";
                    must "../add-path-mode='null' or not(../add-path-mode) or ../advertise-best-external='false'";
                    must "not(../add-path-number and ../advertise-best-external='true')";
                    default "false";
                    description
                      "Enable/disable the device to advertise Best External routes to peers.";
                  }
                  uses advertise-large-community-type;
                  leaf keep-all-routes {
                    when "/bgp:bgp/bgp:base-process/bgp:keep-all-routes='false'";
                    type boolean;
                    default "false";
                    description
                      "Enable/disable saving all the updated information about BGP routes from a specified peer or peer group after a BGP connection is established, even though these BGP routes fail to match the routing policy on the ingress. By default, the updated information about BGP routes from a specified peer is saved only when the routes match the routing policy on the ingress. If a router supports route refreshing, this option is not required.";
                  }
                  uses route-limit-type;
                  uses public-as-only-type;
                  uses path-attr-map-type;
                }
                container ipv4-labeluni {
                  when "../type = 'ipv4labeluni'";
                  description
                    "Configure IPv4 label unicast options.";
                  leaf group-name {
                    type leafref {
                      path "../../../../../../peer-groups/peer-group/name";
                    }
                    must "../../../../../../peer-groups/peer-group[name = current()]/afs/af[type = 'ipv4labeluni']";
                    description
                      "Configure a name for a peer group. After a peer is deleted from the peer group, the peer is disabled from the address family. The object cannot be modified.";
                    ext:operation-exclude update {
                      description "The node cannot be modified, when the peer already belongs to a peer-group.";
                    }
                  }
                  leaf advertise-community {
                    type boolean;
                    default "false";
                    description
                      "Enable/disable advertise the community attribute to a peer or a peer group.";
                  }
                  leaf reflect-client {
                    type boolean;
                    default "false";
                    description
                      "Enable/disable the local device as a route reflector (RR) and a peer or peer group as its client. This configuration is applicable between IBGP peers only. The configurations of RRs and its clients in an address family are valid only in this address family. Therefore, it is recommended to configure RRs and its clients in the specified address family that is required.";
                  }
                  leaf check-tunnel-reachable {
                    type boolean;
                    default "false";
                    description
                      "Enable/disable tunnel reachability check.";
                  }
                  choice import-policy-type {
                    description
                      "Set route policy or filter.";
                    case rtp-ref {
                      description
                        "Route policy.";
                      leaf import-policy {
                        type leafref {
                          path "/rtp:routing-policy/rtp:policy-definitions/rtp:policy-definition/rtp:name";
                        }
                        description
                          "Specify the filtering policy applied to the routes learned from a peer. By default, no such policy is specified.";
                      }
                    }
                  }
                  choice export-policy-type {
                    description
                      "Set route policy or filter.";
                    case rtp-ref {
                      description
                        "Route policy.";
                      leaf export-policy {
                        type leafref {
                          path "/rtp:routing-policy/rtp:policy-definitions/rtp:policy-definition/rtp:name";
                        }
                        description
                          "Specify the filtering policy applied to the routes to be advertised to a peer. By default, no such policy is specified.";
                      }
                    }
                  }
                  leaf advertise-ext-community {
                    type boolean;
                    default "false";
                    description
                      "Enable/disable advertise the extended community attribute to a peer or peer group.";
                  }
                  leaf discard-ext-community {
                    type boolean;
                    default "false";
                    description
                      "Enable/disable discard the extended community attribute in the routing information about a specified peer.";
                  }
                  leaf allow-as-loop {
                    type uint32 {
                      range "1..10";
                    }
                    description
                      "Allow repetitive local AS numbers. By default, repetitive local AS numbers are not allowed.";
                  }
                  leaf aigp {
                    when "../../../../../../../../ni:name='_public_'";
                    type boolean;
                    default "false";
                    description
                      "Enable/disable route with AIGP attribute advertisement to or from a peer.";
                  }
                  leaf add-path-mode {
                    when "../../../../../../../../ni:name='_public_'";
                    type add-path-cap-type;
                    default "null";
                    description
                      "Enable add-path route advertisement to a peer.";
                  }
                  uses ip-prefix-filter-type;
                  uses as-path-filter-type;
                  uses rt-update-interval-type;
                  leaf nexthop-configure {
                    type nexthop-configuration-type;
                    description
                      "Both the next-hop-local mode and next-hop-invariable mode are available when the peer address family is the VPNv4/VPNV6/L2VPN AD address family. Only the next-hop-local mode is available when the peer address family is not VPNv4/VPNV6/L2VPN AD address family. In next-hop-local mode, you can configure a BGP speaker to set its IP address of as the next hop of the routes to be advertised to IBGP peers or IBGP peer groups. In next-hop-invariable mode, you can configure PEs in different ASs not to change the next hop of routes when the PEs advertise the routes to their EBGP peers and use the next hop addresses of IGP routes to advertise imported IGP routes to IBGP peers. By default, when a BGP speaker advertises routes to EBGP peers and imported IGP routes to IBGP peers, the BGP speaker changes the next hop to its interface address.";
                  }
                  uses preferred-value-type;
                  leaf add-path-number {
                    when "../../../../../../../../ni:name='_public_'";
                    type uint8 {
                      range "2..64";
                    }
                    description
                      "Number of Add-Path routes that can be advertised to a peer.";
                  }
                  leaf substitute-as-enable {
                    type boolean;
                    default "false";
                    description
                      "Enable/disable replace the AS number of a specified peer in the AS_Path attribute with the local AS number. On a PE where AS number replacement is enabled, if an AS number in the AS_Path attribute of a route is same as that of the CE to which the PE advertises the route, the PE replaces the AS number with its own AS number before advertising the route.";
                  }
                  leaf soo {
                    when "../../../../../../../../ni:name!='_public_'";
                    type string {
                      length "3..21";
                    }
                    description
                      "Configure the Site-of-Origin (SoO) extended community attribute. This attribute can be expressed in the following formats: X.X.X.X:number<0-65535>, number<0-65535>:number<0-4294967295>, or number<0-65535>.number<0-65535>:number<0-65535> or <65536-4294967295>:<0-65535>. 0:0 or 0.0:0 is not supported. 
                      Two CEs are in the same site and can advertise routes to each other, and they are connected to a VPN through PEs. If the local routes of a CE are advertised to the other CE over the VPN, a routing loop may occur. 
                      The SoO feature can prevent a route advertised by a site from being sent back to the site, preventing routing loops. After SoO is enabled and a PE receives a route from a CE, the specified SoO attribute will be added to the route. Before advertising the route to the other CE, the PE checks the SoO attribute. If the SoO attribute is the same as the locally configured SoO attribute, the PE does not advertise the route, preventing routing loops.";
                  }
                  leaf advertise-best-external {
                    when "../../../../../../../../ni:name='_public_'";
                    type boolean;
                    must "../reflect-client='false' or ../advertise-best-external='false'";
                    must "../add-path-mode='null' or not(../add-path-mode) or ../advertise-best-external='false'";
                    must "not(../add-path-number and ../advertise-best-external='true')";
                    default "false";
                    description
                      "Enable/disable the device to advertise Best External routes to peers.";
                  }
                  leaf load-balancing-enable {
                    when "../../../../../../../../ni:name='_public_'";
                    type boolean;
                    default "false";
                    description
                      "Enable/disable a neighbour to participate in load balancing.";
                  }
                  choice load-balancing-ignore-as-type {
                    description
                      "Set load balancing as path type.";
                    case as-attribute {
                      description
                        "Ignore the as-path attribute.";
                      leaf load-balancing-as-path-ignore {
                        when "../load-balancing-enable='true'";
                        type empty;
                        description
                          "Configure BGP to ignore the AS_Path attribute when selecting the equal route. After as-path-neglect is selected, BGP does not compare the AS_Path length.";
                      }
                    }
                    case same-length-as-attribute {
                      description
                        "Ignore comparison of as-path attributes with the same length.";
                      leaf load-balancing-as-path-relax {
                        when "../load-balancing-enable='true'";
                        type empty;
                        description
                          "Configure BGP to ignore comparison of AS_Path attributes with the same length when selecting the equal route. After as-path-neglect is selected, BGP does not compare the AS_Path length.";
                      }
                    }
                  }
                  uses advertise-large-community-type;
                  uses route-limit-accept-type;
                  uses public-as-only-type;
                  container entropy-label-parameter {
                    when "../../../../../../../../ni:name='_public_'";
                    description
                      "Configure information about entropy label parameter configuration in a peer.";
                    uses peer-entropy-label-type;
                  }
                  uses path-attr-map-type;
                }
                container ipv4-multicast {
                  when "../type='ipv4multi'";
                  description
                    "Configure IPv4 multicast options.";
                  leaf group-name {
                    type leafref {
                      path "../../../../../../peer-groups/peer-group/name";
                    }
                    must "../../../../../../peer-groups/peer-group[name = current()]/afs/af[type = 'ipv4multi']";
                    description
                      "Configure a name for a peer group. After a peer is deleted from the peer group, the peer is disabled from the address family. The object cannot be modified.";
                    ext:operation-exclude update {
                      description "The node cannot be modified, when the peer already belongs to a peer-group.";
                    }
                  }
                  uses default-route-advertise-type;
                  uses ip-prefix-filter-type;
                  uses as-path-filter-type;
                  leaf advertise-ext-community {
                    type boolean;
                    default "false";
                    description
                      "Enable/disable advertise the extended community attribute to a peer or peer group.";
                  }
                  leaf discard-ext-community {
                    type boolean;
                    default "false";
                    description
                      "Enable/disable discard the extended community attribute in the routing information about a specified peer.";
                  }
                  leaf allow-as-loop {
                    type uint32 {
                      range "1..10";
                    }
                    description
                      "Allow repetitive local AS numbers. By default, repetitive local AS numbers are not allowed.";
                  }
                  leaf nexthop-configure {
                    type nexthop-configuration-type;
                    must "../nexthop-configure='local'";
                    description
                      "Both the next-hop-local mode and next-hop-invariable mode are available when the peer address family is the VPNv4/VPNV6/L2VPN AD address family. Only the next-hop-local mode is available when the peer address family is not VPNv4/VPNV6/L2VPN AD address family. In next-hop-local mode, you can configure a BGP speaker to set its IP address of as the next hop of the routes to be advertised to IBGP peers or IBGP peer groups. In next-hop-invariable mode, you can configure PEs in different ASs not to change the next hop of routes when the PEs advertise the routes to their EBGP peers and use the next hop addresses of IGP routes to advertise imported IGP routes to IBGP peers. By default, when a BGP speaker advertises routes to EBGP peers and imported IGP routes to IBGP peers, the BGP speaker changes the next hop to its interface address.";
                  }
                  leaf advertise-community {
                    type boolean;
                    default "false";
                    description
                      "Enable/disable advertise the community attribute to a peer or a peer group.";
                  }
                  leaf keep-all-routes {
                    when "/bgp:bgp/bgp:base-process/bgp:keep-all-routes='false'";
                    type boolean;
                    default "false";
                    description
                      "Enable/disable saving all the updated information about BGP routes from a specified peer or peer group after a BGP connection is established, even though these BGP routes fail to match the routing policy on the ingress. By default, the updated information about BGP routes from a specified peer is saved only when the routes match the routing policy on the ingress. If a router supports route refreshing, this option is not required.";
                  }
                  choice import-policy-type {
                    description
                      "Set route policy or filter.";
                    case rtp-ref {
                      description
                        "Route policy.";
                      leaf import-policy {
                        type leafref {
                          path "/rtp:routing-policy/rtp:policy-definitions/rtp:policy-definition/rtp:name";
                        }
                        description
                          "Specify the filtering policy applied to the routes learned from a peer. By default, no such policy is specified.";
                      }
                    }
                  }
                  choice export-policy-type {
                    description
                      "Set route policy or filter.";
                    case rtp-ref {
                      description
                        "Route policy.";
                      leaf export-policy {
                        type leafref {
                          path "/rtp:routing-policy/rtp:policy-definitions/rtp:policy-definition/rtp:name";
                        }
                        description
                          "Specify the filtering policy applied to the routes to be advertised to a peer. By default, no such policy is specified.";
                      }
                    }
                  }
                  leaf reflect-client {
                    type boolean;
                    default "false";
                    description
                      "Enable/disable the local device as a route reflector (RR) and a peer or peer group as its client. This configuration is applicable between IBGP peers only. The configurations of RRs and its clients in an address family are valid only in this address family. Therefore, it is recommended to configure RRs and its clients in the specified address family that is required.";
                  }
                  uses advertise-large-community-type;
                  uses rt-update-interval-type;
                  uses bgp:preferred-value-type;
                  uses route-limit-type;
                  uses public-as-only-type;
                  uses path-attr-map-type;
                }
                container state {
                  config false;
                  description
                    "Operational state of peer information.";
                  leaf type {
                    type peer-type-info;
                    config false;
                    description
                      "Configures the type of BGP peers: IBGP or EBGP.";
                  }
                  leaf version {
                    type uint8;
                    config false;
                    description
                      "The current BGP version is BGP-4. BGP-4 provides a set of new mechanisms to support Classless Inter-Domain Routing (CIDR). The new mechanisms also support the network prefix-based advertisement, cancellation of the 'class' concept for a BGP network during the network prefix-supported advertisements, and route summarization and AS path summarization.";
                  }
                  leaf remote-router-id {
                    type inet:ipv4-address-no-zone;
                    config false;
                    description
                      "Router ID for a peer.";
                  }
                  leaf current-state {
                    type peer-state;
                    config false;
                    description
                      "Current BGP state, which can be Idle, Active, Established, Connect, OpenSent, or OpenConfirm.
Idle: In this state, BGP denies all connection requests. This is the initial state of BGP.
Active: In this state, BGP tries to establish TCP connections. This is the intermediate state of BGP.
Established: In this state, BGP peers can exchange Update, Notification, and Keepalive packets with each other.
Connect: In this state, BGP determines the subsequent operation after the TCP connections are established.
OpenSent: In this state, BGP is waiting for the Open packet from the peer.
OpenConfirm: In this state, BGP is waiting for a Notification packet and a Keepalive packet.";
                  }
                  leaf local-port {
                    type uint32;
                    config false;
                    description
                      "Local port number. BGP uses TCP as the transport layer protocol, and the port number of the TCP connection initiator is 179.";
                  }
                  leaf remote-port {
                    type uint32 {
                      range "0..4294967295";
                    }
                    config false;
                    description
                      "Port number for a peer to establish a peer relationship.";
                  }
                  leaf current-event {
                    type string {
                      length "1..39";
                    }
                    config false;
                    description
                      "Recent event that occurs on a peer.";
                  }
                  leaf last-state {
                    type peer-state;
                    config false;
                    description
                      "Last state of a peer, which can be Idle, Connect, Active, OpenSent, OpenConfirm, or Established.";
                  }
                  leaf up-down-duration {
                    type string {
                      length "1..49";
                    }
                    config false;
                    description
                      "Duration in which a BGP peer is in the Up or Down state.
The Up state indicates the established state, and the Down state indicates a non-established state (including the Idle, Active, Connect, OpenSent and OpenConfirm state). When the state is switched between Up and Down, the upDownDuration timer is reset and starts from 0.";
                  }
                  leaf send-message {
                    type uint32 {
                      range "0..4294967295";
                    }
                    config false;
                    description
                      "Number of messages sent to the peer.";
                  }
                  leaf rpd-capability {
                    type rpd-cap-type;
                    config false;
                    description
                      "Peer route-policy distribute capability.";
                  }
                  leaf local-rpd-capability {
                    type rpd-cap-type;
                    config false;
                    description
                      "Local route-policy distribute capability.";
                  }
                  leaf negotiate-rpd-capability {
                    type rpd-cap-type;
                    config false;
                    description
                      "Negotiated route-policy distribute capability.";
                  }
                  leaf receive-message {
                    type uint32 {
                      range "0..4294967295";
                    }
                    config false;
                    description
                      "Number of messages received from the peer.";
                  }
                  leaf out-queue {
                    type uint32 {
                      range "0..4294967295";
                    }
                    config false;
                    description
                      "Number of messages to be sent in a queue.";
                  }
                  leaf receive-hold-time {
                    type uint32 {
                      range "0..65535";
                    }
                    units "s";
                    config false;
                    description
                      "Hold time of a peer.";
                  }
                  leaf receive-last-keepalive-time {
                    type yang:date-and-time;
                    config false;
                    description
                      "Last time when Keepalive packets were received from a peer.";
                  }
                  leaf negotiate-hold-time {
                    type uint32 {
                      range "0..65535";
                    }
                    units "s";
                    config false;
                    description
                      "Hold time negotiated by BGP peers.";
                  }
                  leaf negotiate-keepalive-time {
                    type uint32 {
                      range "0..21845";
                    }
                    units "s";
                    config false;
                    description
                      "Keepalive time negotiated by BGP peers.";
                  }
                  leaf receive-update-count {
                    type uint32 {
                      range "0..4294967295";
                    }
                    config false;
                    description
                      "Number of Update packets received from a peer.";
                  }
                  leaf receive-open-count {
                    type uint32 {
                      range "0..4294967295";
                    }
                    config false;
                    description
                      "Number of Open packets received from a peer.";
                  }
                  leaf receive-keepalive-count {
                    type uint32 {
                      range "0..4294967295";
                    }
                    config false;
                    description
                      "Number of Keepalive packets received from a peer.";
                  }
                  leaf receive-notification-count {
                    type uint32 {
                      range "0..4294967295";
                    }
                    config false;
                    description
                      "Number of Notification packets received from a peer.";
                  }
                  leaf receive-route-refresh-count {
                    type uint32 {
                      range "0..4294967295";
                    }
                    config false;
                    description
                      "Number of Route-Refresh packets received from a peer.";
                  }
                  leaf send-update-count {
                    type uint32 {
                      range "0..4294967295";
                    }
                    config false;
                    description
                      "Number of Update packets sent to a peer.";
                  }
                  leaf send-open-count {
                    type uint32 {
                      range "0..4294967295";
                    }
                    config false;
                    description
                      "Number of Open packets sent to a peer.";
                  }
                  leaf send-keepalive-count {
                    type uint32 {
                      range "0..4294967295";
                    }
                    config false;
                    description
                      "Number of Keepalive packets sent to a peer.";
                  }
                  leaf send-notification-count {
                    type uint32 {
                      range "0..4294967295";
                    }
                    config false;
                    description
                      "Number of Notification packets sent to a peer.";
                  }
                  leaf send-route-refresh-count {
                    type uint32 {
                      range "0..4294967295";
                    }
                    config false;
                    description
                      "Number of Route-Refresh packets sent to a peer.";
                  }
                  leaf send-graceful-restart-capability {
                    type boolean;
                    config false;
                    description
                      "Whether the local end supports the GR (Graceful Restart) capability.";
                  }
                  leaf receive-refresh-capability {
                    type boolean;
                    config false;
                    description
                      "Whether the peer supports RR.";
                  }
                  leaf receive-four-byte-as-capability {
                    type boolean;
                    config false;
                    description
                      "Whether the peer supports 4-byte AS numbers.";
                  }
                  leaf receive-multi-protocol-capability {
                    type boolean;
                    config false;
                    description
                      "Whether the peer supports MP.";
                  }
                  leaf receive-graceful-restart-capability {
                    type boolean;
                    config false;
                    description
                      "Whether the peer supports GR.";
                  }
                  leaf receive-add-path {
                    type string {
                      length "1..50";
                    }
                    config false;
                    description
                      "Whether the peer supports Add-Path.";
                  }
                  leaf negotiate-add-path {
                    type string {
                      length "1..50";
                    }
                    config false;
                    description
                      "Negotiated Add-Path.";
                  }
                  leaf receive-label-add-path {
                    type string {
                      length "1..50";
                    }
                    config false;
                    description
                      "Whether the peer supports labeled Add-Path.";
                  }
                  leaf negotiate-label-add-path {
                    type string {
                      length "1..50";
                    }
                    config false;
                    description
                      "Negotiated Label Add-Path.";
                  }
                  leaf receive-prefix {
                    type uint32 {
                      range "0..4294967295";
                    }
                    config false;
                    description
                      "Number of received route prefixes.";
                  }
                  leaf receive-active-prefix {
                    type uint32 {
                      range "0..4294967295";
                    }
                    config false;
                    description
                      "Number of received prefixes of active routes.";
                  }
                  leaf advertise-prefix {
                    type uint32 {
                      range "0..4294967295";
                    }
                    config false;
                    description
                      "Number of advertised route prefixes.";
                  }
                  leaf discard-attribute {
                    type string {
                      length "1..300";
                    }
                    config false;
                    description
                      "The attribute id discard info.";
                  }
                  leaf check-first-as {
                    type first-as-state;
                    config false;
                    description
                      "Check the first AS in the AS_Path of the update messages from EBGP peers.";
                  }
                  leaf extend-nexthop-capability {
                    type boolean;
                    config false;
                    description
                      "Peer extended next hop encoding capability.";
                  }
                  leaf egress-engineer-capability {
                    type boolean;
                    config false;
                    description
                      "Whether the peer supports EPE.";
                  }
                  leaf orf-capability {
                    type boolean;
                    config false;
                    description
                      "Whether the peer supports VPN orf capability.";
                  }
                  leaf rely-interface-capability {
                    type boolean;
                    config false;
                    description
                      "Whether the peer supports check interface.";
                  }
                  leaf remote-as {
                    type string {
                      length "1..11";
                    }
                    config false;
                    description
                      "AS number of the BGP peer.";
                  }
                  leaf memory-priority {
                    type memory-priority;
                    description
                      "Priority that is used to determine the disconnection order of a BGP peer relationship if memory overload occurs.";
                  }
                }
              }
            }
          }
        }
        container peer-bfd-session-states {
          config false;
          description
            "List of BFD sessions.";
          list peer-bfd-session-state {
            key "address";
            config false;
            description
              "Operational state of BFD session.";
            leaf address {
              type inet:ip-address-no-zone;
              config false;
              description
                "Peer address of the BFD session.";
            }
            leaf local-address {
              type inet:ip-address-no-zone;
              config false;
              description
                "Local address of the BFD session.";
            }
            leaf if-name {
              type pub-type:if-name;
              config false;
              description
                "Name of an interface of the BFD session.";
            }
            leaf tx-interval {
              type uint32;
              units "ms";
              default "0";
              config false;
              description
                "Interval at which BFD packets are sent.";
            }
            leaf rx-interval {
              type uint32;
              units "ms";
              default "0";
              config false;
              description
                "Interval at which BFD packets are received.";
            }
            leaf multiplier {
              type uint32 {
                range "0..50";
              }
              config false;
              description
                "Detection multiplier.";
            }
            leaf status {
              type bfd-state;
              config false;
              description
                "State of the BFD session.";
            }
            leaf global-bfd-enable {
              type boolean;
              config false;
              description
                "Global BFD state.";
            }
          }
        }
        container egress-engineer-peer-sets {
          when "../../../ni:name='_public_'";
          description
            "List of peer set information under BGP instance.";
          list egress-engineer-peer-set {
            key "peer-set-name";
            description
              "Configure peer set information.";
            leaf peer-set-name {
              type string {
                length "1..63";
              }
              description
                "The name for peer set.";
            }
            leaf static-label {
              type uint32;
              description
                "The static label for peer set.";
            }
            leaf label-pop {
              when "../static-label";
              type boolean;
              must "not(../relate-bfd='true' and ../label-pop='true')";
              default "false";
              description
                "Enable/disable the BGP-EPE label popping function.";
            }
            leaf relate-bfd {
              type boolean;
              must "not(../relate-bfd='true' and ../label-pop='true')";
              default "false";
              description
                "Enable/disable association between the BGP-EPE label and BFD status.";
            }
          }
        }
      }
    }
  }
}
