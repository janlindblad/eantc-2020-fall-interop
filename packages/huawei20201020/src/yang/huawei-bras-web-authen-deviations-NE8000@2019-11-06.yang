/*
Copyright (C) 2019 Huawei Technologies Co., Ltd. All rights reserved.
*/
module huawei-bras-web-authen-deviations-NE8000 {
  namespace "urn:huawei:yang:huawei-bras-web-authen-deviations-NE8000";
  prefix bras-web-authen-devs-NE8000;

  import huawei-bras-web-authen {
    prefix bras-web-authen;
  }

  import huawei-aaa {
    prefix aaa;
  }

  import huawei-bras-basic-access {
    prefix bras-basic-access;
  }

  organization
    "Huawei Technologies Co., Ltd.";

  contact
    "Huawei Industrial Base
     Bantian, Longgang
     Shenzhen 518129
     People's Republic of China
     Website: http://www.huawei.com
     Email: support@huawei.com";

  description
    "This module defines deviation statements for huawei-bras-web-authen module.";

  revision 2019-11-06 {
    description
      "Initial revision.";
    reference
      "Huawei private.";
  }

  deviation "/bras-web-authen:bras-web-authen" {
    deviate not-supported;
  }
  deviation "/aaa:aaa/aaa:domains/aaa:domain/bras-basic-access:bas/bras-web-authen:web-authen" {
    deviate not-supported;
  }

}
