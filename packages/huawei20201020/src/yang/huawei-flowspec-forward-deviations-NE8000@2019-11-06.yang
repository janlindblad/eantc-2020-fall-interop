/*
Copyright (C) 2019 Huawei Technologies Co., Ltd. All rights reserved.
*/
module huawei-flowspec-forward-deviations-NE8000 {
  namespace "urn:huawei:yang:huawei-flowspec-forward-deviations-NE8000";
  prefix flowspec-forward-devs-NE8000;

  import huawei-flowspec-forward {
    prefix flowspec-forward;
  }

  import huawei-devm {
    prefix devm;
  }

  organization
    "Huawei Technologies Co., Ltd.";

  contact
    "Huawei Industrial Base
     Bantian, Longgang
     Shenzhen 518129
     People's Republic of China
     Website: http://www.huawei.com
     Email: support@huawei.com";

  description
    "This module defines deviation statements for huawei-flowspec-forward module.";

  revision 2019-11-06 {
    description
      "Initial revision.";
    reference
      "Huawei private.";
  }

  deviation "/devm:devm/devm:lpu-boards/devm:lpu-board/flowspec-forward:flowspec-forward" {
    deviate not-supported;
  }

}
