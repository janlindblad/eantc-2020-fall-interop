/*
Copyright (C) 2019 Huawei Technologies Co., Ltd. All rights reserved.
*/
module huawei-ifit-fwd-notification {
  yang-version 1;
  namespace "urn:huawei:yang:huawei-ifit-fwd-notification";
  prefix ifit-fwd-notification;
  import huawei-extension {
    prefix ext;
  }
  organization
    "Huawei Technologies Co., Ltd.";
  contact
    "Huawei Industrial Base
    Bantian, Longgang
    Shenzhen 518129
    People's Republic of China
    Website: http://www.huawei.com
    Email: support@huawei.com";
  description
    "Notification of ifit-fwd-notification.";
  revision 2019-07-08 {
    description
      "Initial revision.";
    reference
      "Huawei private.";
  }
  ext:task-name "ifit";
  notification ifit-dynamic-flow-exceed {
    description
      "The total number of iFIT dynamic flows on the interface board reached the upper limit.";
    leaf slot-id {
      type string {
        length "1..32";
      }
      description
        "Slot ID of an interface board.";
    }
    leaf flow-limit-num {
      type uint32;
      description
        "Maximum number of iFIT Instances on the interface board.";
    }
  }
  notification ifit-dynamic-flow-exceed-resume {
    description
      "The total number of iFIT dynamic flows on the interface board fell below the upper limit.";
    leaf slot-id {
      type string {
        length "1..32";
      }
      description
        "Slot ID of an interface board.";
    }
    leaf flow-limit-num {
      type uint32;
      description
        "Maximum number of iFIT Instances on the interface board.";
    }
  }
  notification ifit-static-flow-exceed {
    description
      "The total number of iFIT static flows on the interface board reached the upper limit.";
    leaf slot-id {
      type string {
        length "1..32";
      }
      description
        "Slot ID of an interface board.";
    }
    leaf flow-limit-num {
      type uint32;
      description
        "Maximum number of iFIT Instances on the interface board.";
    }
  }
  notification ifit-static-flow-exceed-resume {
    description
      "The total number of iFIT static flows on the interface board fell below the upper limit.";
    leaf slot-id {
      type string {
        length "1..32";
      }
      description
        "Slot ID of an interface board.";
    }
    leaf flow-limit-num {
      type uint32;
      description
        "Maximum number of iFIT Instances on the interface board.";
    }
  }
}
