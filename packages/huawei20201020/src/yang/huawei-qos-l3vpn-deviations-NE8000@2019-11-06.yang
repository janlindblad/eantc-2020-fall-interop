/*
Copyright (C) 2019 Huawei Technologies Co., Ltd. All rights reserved.
*/
module huawei-qos-l3vpn-deviations-NE8000 {
  namespace "urn:huawei:yang:huawei-qos-l3vpn-deviations-NE8000";
  prefix qos-l3vpn-devs-NE8000;

  import huawei-qos-l3vpn {
    prefix qos-l3vpn;
  }

  import huawei-network-instance {
    prefix ni;
  }

  organization
    "Huawei Technologies Co., Ltd.";

  contact
    "Huawei Industrial Base
     Bantian, Longgang
     Shenzhen 518129
     People's Republic of China
     Website: http://www.huawei.com
     Email: support@huawei.com";

  description
    "This module defines deviation statements for huawei-qos-l3vpn module.";

  revision 2019-11-06 {
    description
      "Initial revision.";
    reference
      "Huawei private.";
  }

  deviation "/ni:network-instance/ni:instances/ni:instance/qos-l3vpn:qos-l3vpn/qos-l3vpn:vxlan-car-disables" {
    deviate not-supported;
  }

}
