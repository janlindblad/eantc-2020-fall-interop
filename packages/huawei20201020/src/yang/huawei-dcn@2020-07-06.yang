/*
Copyright (C) 2020 Huawei Technologies Co., Ltd. All rights reserved.
*/
module huawei-dcn {
  yang-version 1;
  namespace "urn:huawei:yang:huawei-dcn";
  prefix dcn;
  import huawei-extension {
    prefix ext;
  }
  import huawei-ifm {
    prefix ifm;
  }  
  organization
    "Huawei Technologies Co., Ltd.";
  contact
    "Huawei Industrial Base
    Bantian, Longgang
    Shenzhen 518129
    People's Republic of China
    Website: http://www.huawei.com
    Email: support@huawei.com";
  description
    "Data communication network.";
  revision 2020-07-06 {
    description
      "Init revision.";
    reference
      "Huawei private.";
  }
  
  ext:task-name "dcn";
  container dcn {
    description
      "Data communication network.";
    container site {
      description
        "Configure data communication network.";
      leaf enable {
        type boolean;
        default "true";
        description
          "Enable/disable DCN.";
      }
    }
  }
  augment /ifm:ifm/ifm:interfaces/ifm:interface {
    description
      "DCN interface configuration.";
    container dcn {
      when "/dcn:dcn/dcn:site/dcn:enable = 'true'";
      description
        "Configure DCN interface.";
      container dcnv4 {
        description
          "Configure DCN interface.";
        leaf default-port {
          type boolean;
          ext:operation-exclude "create|delete|update";
          description
            "Enable/disable auto enable DCN.";
        }
        leaf enable {
          type boolean;
            ext:dynamic-default {
            ext:default-value "true" {
              when "/dcn:dcn/dcn:site/dcn:enable = 'true' and ../default-port = 'true'";
              description "DCN is enabled on a default DCN port when the global DCN is enabled.";
            }
          }
          description
            "Enable/disable DCN.";
        }
      }
      container tc-dcn {
        description
          "Configure TC DCN interface.";
        leaf default-port {
          type boolean;
          ext:operation-exclude "create|delete|update";
          description
            "Enable/disable auto enable TC DCN.";
        }
        leaf enable {
          type boolean;
          ext:dynamic-default {
            ext:default-value "true" {
              when "/dcn:dcn/dcn:site/dcn:enable = 'true' and ../default-port = 'true'";
              description "TC DCN is enabled on a default TC DCN port when the global DCN is enabled.";
            }
          }
          description
            "Enable/disable TC DCN.";
        }
      }
    }
  }
}
