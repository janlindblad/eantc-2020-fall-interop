/*
Copyright (C) 2019-2020 Huawei Technologies Co., Ltd. All rights reserved.
*/
module huawei-acl-ucl-deviations-NE8000 {
  yang-version 1;
  namespace "urn:huawei:yang:huawei-acl-ucl-deviations-NE8000";
  prefix acl-ucl-devs-NE8000;

  import huawei-acl {
    prefix acl;
  }
  import huawei-acl-ucl {
    prefix acl-ucl;
  }

  organization
    "Huawei Technologies Co., Ltd.";
  contact
    "Huawei Industrial Base
     Bantian, Longgang
     Shenzhen 518129
     People's Republic of China
     Website: http://www.huawei.com
     Email: support@huawei.com";
  description
    "Global Configuration.";

  revision 2020-02-20 {
    description
      "The deviations of the huawei-acl-ucl module were modified.";
    reference "Huawei private.";
  }
  revision 2019-06-25 {
    description
      "Init revision.";
    reference "Huawei private.";
  }

  deviation "/acl:acl/acl:group6s/acl:group6/acl-ucl:rule-ucls/acl-ucl:rule-ucl/acl-ucl:protocol-type/acl-ucl:zero" {
    deviate not-supported;
  }
  deviation "/acl:acl/acl:groups/acl:group/acl-ucl:rule-ucls/acl-ucl:rule-ucl/acl-ucl:source/acl-ucl:src-user-group" {
    deviate not-supported;
  }
  deviation "/acl:acl/acl:groups/acl:group/acl-ucl:rule-ucls/acl-ucl:rule-ucl/acl-ucl:source/acl-ucl:src-user-group-any" {
    deviate not-supported;
  }
  deviation "/acl:acl/acl:groups/acl:group/acl-ucl:rule-ucls/acl-ucl:rule-ucl/acl-ucl:dest/acl-ucl:dest-user-group" {
    deviate not-supported;
  }
  deviation "/acl:acl/acl:groups/acl:group/acl-ucl:rule-ucls/acl-ucl:rule-ucl/acl-ucl:dest/acl-ucl:dest-user-group-any" {
    deviate not-supported;
  }
  deviation "/acl:acl/acl:group6s/acl:group6/acl-ucl:rule-ucls/acl-ucl:rule-ucl/acl-ucl:source/acl-ucl:src-user-group" {
    deviate not-supported;
  }
  deviation "/acl:acl/acl:group6s/acl:group6/acl-ucl:rule-ucls/acl-ucl:rule-ucl/acl-ucl:source/acl-ucl:src-user-group-any" {
    deviate not-supported;
  }
  deviation "/acl:acl/acl:group6s/acl:group6/acl-ucl:rule-ucls/acl-ucl:rule-ucl/acl-ucl:dest/acl-ucl:dest-user-group" {
    deviate not-supported;
  }
  deviation "/acl:acl/acl:group6s/acl:group6/acl-ucl:rule-ucls/acl-ucl:rule-ucl/acl-ucl:dest/acl-ucl:dest-user-group-any" {
    deviate not-supported;
  }
}
