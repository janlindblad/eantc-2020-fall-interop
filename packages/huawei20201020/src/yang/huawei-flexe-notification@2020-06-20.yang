/*
Copyright (C) 2020 Huawei Technologies Co., Ltd. All rights reserved.
*/
module huawei-flexe-notification {
  yang-version 1;
  namespace "urn:huawei:yang:huawei-flexe-notification";
  prefix flexe-notification;
  import huawei-extension {
    prefix ext;
  }
  organization
    "Huawei Technologies Co., Ltd.";
  contact
    "Huawei Industrial Base
    Bantian, Longgang
    Shenzhen 518129
    People's Republic of China
    Website: http://www.huawei.com
    Email: support@huawei.com";
  description
    "Notification of flexe module.";
  revision 2020-06-20 {
    description
      "Initial revision.";
    reference
      "Huawei private.";
  }
  ext:task-name  "device-mgr";
  notification flexe-calendar-mismatch {
    description
      "Alarm of mismatch between the actually received and expected client calendars on the FlexE Group.";
    leaf group-index {
      type uint32;
      description
        "Indicates the FlexE group index.";
    }
    leaf group-name {
      type string {
        length "1..32";
      }
      description
        "Indicates the FlexE group name.";
    }
  }
  notification flexe-calendar-mismatch-resume {
    description
      "The alarm of mismatch between the actually received and expected client calendars on the FlexE Group is cleared.";
    leaf group-index {
      type uint32;
      description
        "Indicates the FlexE group index.";
    }
    leaf group-name {
      type string {
        length "1..32";
      }
      description
        "Indicates the FlexE group name.";
    }
  }
  notification flexe-band-mismatch {
    description
      "Indicates the alarm is detected.";
    leaf physical-index {
      type uint32;
      description
        "This object indicates the interface index.";
    }
    leaf physical-port-name {
      type string {
        length "1..32";
      }
      description
        "Indicates the physical port name.";
    }
  }
  notification flexe-band-mismatch-resume {
    description
      "Indicates the alarm is cleared.";
    leaf physical-index {
      type uint32;
      description
        "This object indicates the interface index.";
    }
    leaf physical-port-name {
      type string {
        length "1..32";
      }
      description
        "Indicates the physical port name.";
    }
  }
  notification flexe-band-insufficient {
    description
      "This object indicates an alarm that the existing bandwidth does not meet the configuration requirements.";
    leaf physical-index {
      type uint32;
      description
        "This object indicates the interface index.";
    }
    leaf physical-port-name {
      type string {
        length "1..32";
      }
      description
        "Indicates the physical port name.";
    }
    leaf port-bw {
      type string {
        length "1..32";
      }
      description
        "Indicates the physical port name.";
    }
  }
  notification flexe-band-insufficient-resume {
    description
      "This object indicates a clear alarm that the existing bandwidth does not meet the configuration requirements.";
    leaf physical-index {
      type uint32;
      description
        "This object indicates the interface index.";
    }
    leaf physical-port-name {
      type string {
        length "1..32";
      }
      description
        "Indicates the physical port name.";
    }
    leaf port-bw {
      type string {
        length "1..32";
      }
      description
        "Indicates the physical port name.";
    }
  }
  notification flexe-client-mismatch {
    description
      "Indicates the alarm is detected.";
    leaf physical-index {
      type uint32;
      description
        "This object indicates the interface index.";
    }
    leaf physical-port-name {
      type string {
        length "1..32";
      }
      description
        "Indicates the physical port name.";
    }
  }
  notification flexe-client-mismatch-resume {
    description
      "Indicates the alarm is cleared.";
    leaf physical-index {
      type uint32;
      description
        "This object indicates the interface index.";
    }
    leaf physical-port-name {
      type string {
        length "1..32";
      }
      description
        "Indicates the physical port name.";
    }
  }
  notification flexe-physical-delay {
    description
      "This object indicates that an alarm is generated when the delay difference between FlexE physical interfaces in the same group is too large.";
    leaf physical-index {
      type uint32;
      description
        "This object indicates the interface index.";
    }
    leaf physical-port-list {
      type string {
        length "1..32";
      }
      description
        "Indicates the physical port list.";
    }
  }
  notification flexe-physical-delay-resume {
    description
      "This object indicates that the clear alarm is generated when the delay difference between FlexE physical interfaces in the same group is too large.";
    leaf physical-index {
      type uint32;
      description
        "This object indicates the interface index.";
    }
    leaf physical-port-list {
      type string {
        length "1..32";
      }
      description
        "Indicates the physical port list.";
    }
  }
  notification flexe-physical-fcs-sd {
    description
      "This object indicates that an alarm is generated when MAC FCS SD alarm notification.";
    leaf physical-index {
      type uint32;
      description
        "This object indicates the interface index.";
    }
    leaf physical-port-name {
      type string {
        length "1..32";
      }
      description
        "Indicates the physical port name.";
    }
  }
  notification flexe-physical-fcs-sd-resume {
    description
      "This object indicates that a clear alarm is generated when MAC FCS SD alarm notification.";
    leaf physical-index {
      type uint32;
      description
        "This object indicates the interface index.";
    }
    leaf physical-port-name {
      type string {
        length "1..32";
      }
      description
        "Indicates the physical port name.";
    }
  }
  notification flexe-group-mismatch {
    description
      "This object indicates that an alarm is generated when the group ID of the physical interface does not match.";
    leaf physical-index {
      type uint32;
      description
        "This object indicates the interface index.";
    }
    leaf physical-port-name {
      type string {
        length "1..32";
      }
      description
        "Indicates the physical port name.";
    }
    leaf physical-port-local-groupid {
      type uint32;
      description
        "Indicates the local physical port groupid.";
    }
    leaf physical-port-remte-groupid {
      type uint32;
      description
        "Indicates the remote physical port groupID.";
    }
  }
  notification flexe-group-mismatch-resume {
    description
      "This object indicates that the clear alarm is generated when the group ID of the physical interface does not match.";
    leaf physical-index {
      type uint32;
      description
        "This object indicates the interface index.";
    }
    leaf physical-port-name {
      type string {
        length "1..32";
      }
      description
        "Indicates the physical port name.";
    }
    leaf physical-port-local-groupid {
      type uint32;
      description
        "Indicates the local physical port groupid.";
    }
    leaf physical-port-remte-groupid {
      type uint32;
      description
        "Indicates the remote physical port groupID.";
    }
  }
  notification flexe-local-fault {
    description
      "This object indicates that an alarm is generated when the receive link from the remote device to the local device fails.";
    leaf physical-index {
      type uint32;
      description
        "This object indicates the interface index.";
    }
    leaf physical-port-name {
      type string {
        length "1..32";
      }
      description
        "Indicates the physical port name.";
    }
  }
  notification flexe-local-fault-resume {
    description
      "This object indicates that a clear alarm is generated when the receive link from the remote device to the local device recovers.";
    leaf physical-index {
      type uint32;
      description
        "This object indicates the interface index.";
    }
    leaf physical-port-name {
      type string {
        length "1..32";
      }
      description
        "Indicates the physical port name.";
    }
  }
  notification flexe-number-mismatch {
    description
      "This object indicates that an alarm is generated when the communication parameter number of the physical interfaces do not match.";
    leaf physical-index {
      type uint32;
      description
        "This object indicates the interface index.";
    }
    leaf physical-port-name {
      type string {
        length "1..32";
      }
      description
        "Indicates the physical port name.";
    }
    leaf physical-port-local-phy-num {
      type string {
        length "1..32";
      }
      description
        "Indicates the local physical port phy number.";
    }
    leaf physical-port-remote-phy-num {
      type string {
        length "1..32";
      }
      description
        "Indicates the remote physical port phy number.";
    }
  }
  notification flexe-number-mismatch-resume {
    description
      "This object indicates that a clear alarm is generated when the communication parameter number of the physical interfaces do not match.";
    leaf physical-index {
      type uint32;
      description
        "This object indicates the interface index.";
    }
    leaf physical-port-name {
      type string {
        length "1..32";
      }
      description
        "Indicates the physical port name.";
    }
    leaf physical-port-local-phy-num {
      type string {
        length "1..32";
      }
      description
        "Indicates the local physical port phy number.";
    }
    leaf physical-port-remote-phy-num {
      type string {
        length "1..32";
      }
      description
        "Indicates the remote physical port phy number.";
    }
  }
  notification flexe-remote-fault {
    description
      "This object indicates that an alarm is generated when the transmit link from the remote device to the local device fails.";
    leaf physical-index {
      type uint32;
      description
        "This object indicates the interface index.";
    }
    leaf physical-port-name {
      type string {
        length "1..32";
      }
      description
        "Indicates the physical port name.";
    }
  }
  notification flexe-remote-fault-resume {
    description
      "This object indicates that a clear alarm is generated when the transmit link from the remote device to the local device recovers.";
    leaf physical-index {
      type uint32;
      description
        "This object indicates the interface index.";
    }
    leaf physical-port-name {
      type string {
        length "1..32";
      }
      description
        "Indicates the alarm is cleared.";
    }
  }
  notification flexe-sub-ts-mismatch {
    description
      "This object indicates that an alarm is generated when the sub-timeslot granularity of the interface does not match.";
    leaf physical-index {
      type uint32;
      description
        "This object indicates the interface index.";
    }
    leaf physical-port-name {
      type string {
        length "1..32";
      }
      description
        "Indicates the alarm is cleared.";
    }
  }
  notification flexe-sub-ts-mismatch-resume {
    description
      "This object indicates that a clear alarm is generated when the sub-timeslot granularity of the interface does not match.";
    leaf physical-index {
      type uint32;
      description
        "This object indicates the interface index.";
    }
    leaf physical-port-name {
      type string {
        length "1..32";
      }
      description
        "Indicates the alarm is cleared.";
    }
  }
  notification flexe-negotiation-fail {
    description
      "FlexE group negotiation fail alarm.";
    leaf group-index {
      type uint32;
      description
        "Indicates the FlexE group index.";
    }
    leaf group-name {
      type string {
        length "1..32";
      }
      description
        "Indicates the FlexE group name.";
    }
  }
  notification flexe-negotiation-fail-resume {
    description
      "FlexE group negotiation fail alarm resume.";
    leaf group-index {
      type uint32;
      description
        "Indicates the FlexE group index.";
    }
    leaf group-name {
      type string {
        length "1..32";
      }
      description
        "Indicates the FlexE group name.";
    }
  }
  notification flexe-speed-mismatch {
    description
      "The speed modes of the FlexE physical interfaces in the FlexE group mismatch alarm.";
    leaf group-index {
      type uint32;
      description
        "Indicates the FlexE group index.";
    }
    leaf group-name {
      type string {
        length "1..32";
      }
      description
        "Indicates the FlexE group name.";
    }
  }
  notification flexe-speed-mismatch-resume {
    description
      "The speed modes of the FlexE physical interfaces in the FlexE group mismatch alarm resume.";
    leaf group-index {
      type uint32;
      description
        "Indicates the FlexE group index.";
    }
    leaf group-name {
      type string {
        length "1..32";
      }
      description
        "Indicates the FlexE group name.";
    }
  }
}
