module huawei20201020-nc {
  yang-version 1.1;
  namespace "http://tail-f.com/ns/ned-id/huawei20201020-nc";
  prefix huawei20201020-nc;

  import tailf-common {
    prefix tailf;
  }

  import tailf-ncs-ned {
    prefix ned;
  }

  identity huawei20201020-nc {
    tailf:abstract;
    base ned:netconf-ned-id;
  }
}
