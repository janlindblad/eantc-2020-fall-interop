module nx20200720-nc {
  yang-version 1.1;
  namespace "http://tail-f.com/ns/ned-id/nx20200720-nc";
  prefix nx20200720-nc;

  import tailf-common {
    prefix tailf;
  }

  import tailf-ncs-ned {
    prefix ned;
  }

  identity nx20200720-nc {
    tailf:abstract;
    base ned:netconf-ned-id;
  }
}
