module huawei-openconfig-bgp-deviations-NE8000 {
  yang-version 1;
  namespace "urn:huawei:yang:huawei-openconfig-bgp-deviations-NE8000";
  prefix of-bgp-devs-NE8000;

  import openconfig-bgp {
    prefix oc-bgp;
  }

  organization
    "Huawei Technologies Co.,Ltd.";
  contact
    "Huawei Industrial Base Bantian, Longgang Shenzhen 518129
        People's Republic of China
        Website: http://www.huawei.com Email: support@huawei.com";

  revision 2020-10-10;

  deviation "/oc-bgp:bgp" {
    deviate not-supported;
  }
}
