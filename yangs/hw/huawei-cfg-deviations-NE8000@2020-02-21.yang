/*
Copyright (C) 2020 Huawei Technologies Co., Ltd. All rights reserved.
*/
module huawei-cfg-deviations-NE8000 {
  namespace "urn:huawei:yang:huawei-cfg-deviations-NE8000";
  prefix cfg-devs-NE8000;

  import huawei-cfg {
    prefix cfg;
  }

  organization
    "Huawei Technologies Co., Ltd.";
  contact
    "Huawei Industrial Base
     Bantian, Longgang
     Shenzhen 518129
     People's Republic of China
     Website: http://www.huawei.com
     Email: support@huawei.com";
  description
    "Configuration management module.";

  revision 2020-02-21 {
    description
      "Init revision.";
    reference "Huawei private.";
  }

  deviation "/cfg:create-user-label-checkpoint" {
    deviate not-supported;
  }
}
