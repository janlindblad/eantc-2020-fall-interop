/*
Copyright (C) 2019 Huawei Technologies Co., Ltd. All rights reserved.
*/
module huawei-bras-multicast-deviations-NE8000 {
  namespace "urn:huawei:yang:huawei-bras-multicast-deviations-NE8000";
  prefix bras-multicast-devs-NE8000;

  import huawei-bras-multicast {
    prefix bras-multicast;
  }

  import huawei-aaa {
    prefix aaa;
  }

  import huawei-ifm {
    prefix ifm;
  }

  import huawei-devm {
    prefix devm;
  }

  import huawei-bras-basic-access {
    prefix bras-basic-access;
  }

  organization
    "Huawei Technologies Co., Ltd.";

  contact
    "Huawei Industrial Base
     Bantian, Longgang
     Shenzhen 518129
     People's Republic of China
     Website: http://www.huawei.com
     Email: support@huawei.com";

  description
    "This module defines deviation statements for huawei-bras-multicast module.";

  revision 2019-11-06 {
    description
      "Initial revision.";
    reference
      "Huawei private.";
  }

  deviation "/bras-multicast:bras-multicast/bras-multicast:bas-policy" {
    deviate not-supported;
  }
  deviation "/bras-multicast:bras-multicast/bras-multicast:ipv4-profiles" {
    deviate not-supported;
  }
  deviation "/bras-multicast:bras-multicast/bras-multicast:ipv6-profiles" {
    deviate not-supported;
  }
  deviation "/bras-multicast:bras-multicast/bras-multicast:ipv6-multicast-lists" {
    deviate not-supported;
  }
  deviation "/aaa:aaa/aaa:domains/aaa:domain/bras-basic-access:bas/bras-multicast:multicast" {
    deviate not-supported;
  }
  deviation "/devm:devm/devm:mpu-boards/devm:mpu-board/bras-basic-access:bras/bras-multicast:multicast" {
    deviate not-supported;
  }
  deviation "/devm:devm/devm:lpu-boards/devm:lpu-board/bras-basic-access:bras/bras-multicast:multicast" {
    deviate not-supported;
  }
  deviation "/ifm:ifm/ifm:interfaces/ifm:interface/bras-basic-access:bras/bras-multicast:multicast" {
    deviate not-supported;
  }

}
