module huawei-openconfig-acl-deviations-NE8000 {
  yang-version 1;
  namespace "urn:huawei:yang:huawei-openconfig-acl-deviations-NE8000";
  prefix of-acl-devs-NE8000;

  import openconfig-acl {
    prefix oc-acl;
  }
  import openconfig-packet-match-types {
    prefix oc-pkt-match-types;
  }

  revision 2020-10-11;

  deviation "/oc-acl:acl" {
    deviate not-supported;
  }
}
