/*
Copyright (C) 2020 Huawei Technologies Co., Ltd. All rights reserved.
*/
module huawei-pic-notification {
  yang-version 1;
  namespace "urn:huawei:yang:huawei-pic-notification";
  prefix pic-notification;
  import huawei-extension {
    prefix ext;
  }
  /*
  import huawei-devm {
    prefix devm;
  }
  */
  organization
    "Huawei Technologies Co., Ltd.";
  contact
    "Huawei Industrial Base
    Bantian, Longgang
    Shenzhen 518129
    People's Republic of China
    Website: http://www.huawei.com
    Email: support@huawei.com";
  description
    "Notification of sub-card module.";
  revision 2020-06-20 {
    description
      "Add port notification alarms.";
    reference
      "Huawei private.";
  }
  revision 2020-05-08 {
    description
      "Add four notification alarms.";
    reference
      "Huawei private.";
  }
  revision 2020-03-20 {
    description
      "Initial revision.";
    reference
      "Huawei private.";
  }
  ext:task-name  "device-mgr";
  typedef notification-entity-type {
    type enumeration {
      enum "UNKNOWN" {
        value 0;
        description
          "Unknown.";
      }
      enum "MPU" {
        value 1;
        description
          "MPU.";
      }
      enum "LPU" {
        value 2;
        description
          "LPU.";
      }
      enum "SFU" {
        value 3;
        description
          "SFU.";
      }
      enum "PIC" {
        value 4;
        description
          "PIC.";
      }
      enum "CF-CARD" {
        value 5;
        description
          "CF card.";
      }
      enum "OFC" {
        value 6;
        description
          "OFC.";
      }
    }
    description
      "Physical entity type.";
  }
  typedef notification-probable-cause-type {
    type enumeration {
      enum "unknown" {
        value 0;
        description
          "Unknown.";
      }
      enum "chasis-power-supply-insufficiency"{
        value 131336;
        description
          "The system power or the power of the backup power supply is insufficient.";
      }
      enum "all-sfu-boards-removed"{
        value 131337;
        description
          "No SFU is present in the chassis.";
      }
      enum "all-lpu-boards-removed"{
        value 131338;
        description
          "No LPU is present in the chassis.";
      }
      enum "all-cmu-boards-removed"{
        value 131339;
        description
          "No CMU is present in the chassis.";
      }
      enum "power-supply-module-mismatch-in-frame"{
        value 131340;
        description
          "Communication between the CMUs failed.";
      }
      enum "fail-to-get-slot-information-of-power-supply-module"{
        value 131341;
        description
          "Failed to obtain slot information of the power supply.";
      }
      enum "all-fans-absent"{
        value 131358;
        description
          "All fans are not in position.";
      }
      enum "sfu-board-dismatch-the-frame"{
        value 131586;
        description
          "Different SFUs were installed in the same chassis.";
      }
      enum "the-board-was-removed"{
        value 131840;
        description
          "A board was removed.";
      }
      enum "power-supply-for-a-board-was-abnormal"{
        value 132096;
        description
          "Power supply abnormal.";
      }
      enum "monitor-bus-of-board-partially-failed"{
        value 132097;
        description
          "Board CANBUS failed.";
      }
      enum "board-ce-powered-on-or-powered-off-properly-off"{
        value 132102;
        description
          "Board cannot be powered on or powered off properly.";
      }
      enum "battery-of-mpu-failed"{
        value 132103;
        description
          "Board RTC fault.";
      }
      enum "sensor-on-board-failed"{
        value 132105;
        description
          "The sensor on the board was faulty.";
      }
      enum "flash-memory-memory-on-board-failed"{
        value 132106;
        description
          "Flash memory failed.";
      }
      enum "php-chip-on-board-partially-failed"{
        value 132107;
        description
          "Phy instability.";
      }
      enum "board-pll-malfunctions"{
        value 132128;
        description
          "Board PLL instability.";
      }
      enum "lanswitch-abnormal"{
        value 132134;
        description
          "LANSWITCH chip instability.";
      }
      enum "chip-malfunctions"{
        value 132137;
        description
          "Chip instability.";
      }
      enum "fan-or-power-dismatch-device"{
        value 132162;
        description
          "The fan model or power supply model does not match the device.";
      }
      enum "memory-size-is-different-from-rated"{
        value 132167;
        description
          "The memory size is different from the standard configuration.";
      }
      enum "data-channel-fault-occurred-on-forwarding-engine"{
        value 132189;
        description
          "A data channel fault occurred on the forwarding engine.";
      }
      enum "forward-engine-failed"{
        value 132190;
        description
          "The forwarding engine failed.";
      }
      enum "inter-card-broadcast-traffic-failed-to-be-forwarded"{
        value 132194;
        description
          "Inter-card broadcast traffic failed to be forwarded.";
      }
      enum "fabric-interface-input-or-output-bandwith-usage-exceeded"{
        value 132195;
        description
          "Fabric interface input or output bandwidth usage exceeded 90% continuously.";
      }
      enum "ingress-clock-signals-channel-failed"{
        value 132196;
        description
          "Ingress clock signals channel failed.";
      }
      enum "egress-clock-signals-channel-failed"{
        value 132197;
        description
          "Egress clock signals channel failed.";
      }
      enum "38m-clock-failed"{
        value 132202;
        description
          "The 38M clock fails.";
      }
      enum "packet-reassembly-error-occurred"{
        value 132203;
        description
          "A packet reassembly error occurred.";
      }
      enum "hi-gig-link-on-board-failed"{
        value 132205;
        description
          "The Serdes on the board failed.";
      }
      enum "board-clock-fails"{
        value 132207;
        description
          "The board clock fails.";
      }
      enum "ddr-fault-occurs-on-board"{
        value 132208;
        description
          "A DDR fault occurs on the board.";
      }
      enum "slot-id-of-board-fails-to-be-checked"{
        value 132209;
        description
          "The slot ID of the board fails to be checked.";
      }
      enum "pll-inside-forwarding-engine-is-not-ready"{
        value 132210;
        description
          "The PLL inside the forwarding engine is not ready.";
      }
      enum "internal-modular-of-forwarding-engine-is-abnormal"{
        value 132211;
        description
          "An internal modular of the forwarding engine is abnormal.";
      }
      enum "access-to-flash-memory-of-board-fails"{
        value 132212;
        description
          "Access to the flash memory of the board fails.";
      }
      enum "external-tcam-chip-could-nat-be-accessed"{
        value 132213;
        description
          "The micro switch of the board fails.";
      }
      enum "active-and-standby-mpus-cannot-communicate-with-each-other"{
        value 132214;
        description
          "The active and standby MPUs cannot communicate with each other.";
      }
      enum "fullin-signal-of-board-is-abnormal"{
        value 132215;
        description
          "The FULLIN signal of the board is abnormal.";
      }
      enum "serial-cpld-local-bus-fault-occurs-on-board"{
        value 132216;
        description
          "A SerialCpldLocalbus fault occurs on the board.";
      }
      enum "die-crack-of-cpu-side-occurs-on-board"{
        value 132275;
        description
          "A Die crack of CPU side occurs on the board.";
      }
      enum "die-crack-of-lsw-side-occurs-on-board"{
        value 132276;
        description
          "A Die crack of LSW side occurs on the board.";
      }
      enum "crc-fault-of-lsw-side-occurs-on-board"{
        value 132277;
        description
          "A CRC fault of LSW side occurs on the board.";
      }
      enum "crc-fault-of-cpu-side-occurs-on-board"{
        value 132278;
        description
          "A CRC fault of CPU side occurs on the board.";
      }
      enum "voltage-of-board-fails-to-be-checked"{
        value 132279;
        description
          "The voltage of the board fails to be checked.";
      }
      enum "board-did-not-match-device"{
        value 132610;
        description
          "The board does not match the device.";
      }
      enum "fpga-logic-of-board-was-faulty"{
        value 132613;
        description
          "The FPGA entry of the board may be faulty.";
      }
      enum "epld-logic-of-board-was-faulty"{
        value 132614;
        description
          "The board failed CPLD localbus self-check.";
      }
      enum "clock-signals-failed-on-board"{
        value 132616;
        description
          "The clock signals of the board were incorrect.";
      }
      enum "board-was-power-off"{
        value 132626;
        description
          "The board was powered off.";
      }
      enum "board-registration-failed"{
        value 132627;
        description
          "The board was not registered.";
      }
      enum "board-obtained-abnormal-signals-from-master-and-slave-mpus"{
        value 132630;
        description
          "The board obtained abnormal signals from the master and slave MPUs.";
      }
      enum "board-type-mismatches-preconfiguration"{
        value 132666;
        description
          "The in-position board type conflicts with the pre-configured board type.";
      }
      enum "board-not-support-some-configurations-and-cannot-register"{
        value 132669;
        description
          "The board does not support some configurations and cannot register.";
      }
      enum "usb-overcurrent"{
        value 132670;
        description
          "USB overcurrent.";
      }
      enum "fpga-of-board-was-faulty"{
        value 132674;
        description
          "The FPGA of the board failed.";
      }
      enum "lsw-port-connected-to-mpu-fails"{
        value 132675;
        description
          "The PCIE of the board was faulty.";
      }
      enum "fpga-local-bus-self-test-failed"{
        value 132677;
        description
          "The FPGA local bus self-check failed.";
      }
      enum "notched-register-failed"{
        value 132688;
        description
          "Notched register failed.";
      }
      enum "pcie-link-failed"{
        value 132689;
        description
          "PCIE link failed.";
      }
      enum "master-slave-board-switchover-was-performed"{
        value 133120;
        description
          "The Master/slave Board Switchover Was Performed.";
      }
      enum "subcard-was-removed"{
        value 133376;
        description
          "A card was removed.";
      }
      enum "gephy-chip-on-sub-board-malfunctions"{
        value 135176;
        description
          "Phy instability.";
      }
      enum "chip-on-sub-board-malfunctions"{
        value 135180;
        description
          "The chip on the card fails.";
      }
      enum "phy-register-is-faulty"{
        value 135199;
        description
          "The PHY register is faulty.";
      }
      enum "epld-logic-of-subcard-was-faulty"{
        value 135424;
        description
          "The EPLD logic of the card was faulty.";
      }
      enum "clock-unit-on-subcard-was-faulty"{
        value 135427;
        description
          "The clock on the card failed.";
      }
      enum "card-was-powered-off"{
        value 135439;
        description
          "The card was powered off.";
      }
      enum "subcard-registration-failed-due-to-user-configuration"{
        value 135441;
        description
          "The card failed to be registered.";
      }
      enum "in-position-card-type-conflicts-with-pre-configured-card-type"{
        value 135464;
        description
          "The in-position card type conflicts with the pre-configured card type.";
      }
      enum "optical-module-was-removed"{
        value 135680;
        description
          "The optical module was removed.";
      }
      enum "output-optical-power-was-too-high"{
        value 136193;
        description
          "Output Optical Power Too High.";
      }
      enum "output-optical-power-was-too-low"{
        value 136194;
        description
          "Output Optical Power Too Low.";
      }
      enum "input-optical-power-was-too-high"{
        value 136195;
        description
          "Input Optical Power Too High.";
      }
      enum "input-optical-power-was-too-low"{
        value 136196;
        description
          "Input Optical Power Too Low.";
      }
      enum "optical-model-dismatch"{
        value 136203;
        description
          "Optical Model Dismatch.";
      }
      enum "iic-of-optical-module-failed"{
        value 136231;
        description
          "The IIC of the optical module failed.";
      }
      enum "optical-module-unautorized"{
        value 145920;
        description
          "An optical module that is not certified for Huawei Ethernet switches was installed.";
      }
      enum "some-internal-crc-error-packets-generated-on-sfu"{
        value 147200;
        description
          "A small number of internal CRC error packets are generated on the SFU.";
      }
      enum "packet-loss-occurred-in-queue-on-sfu"{
        value 147201;
        description
          "Packet loss occurred in a queue on an SFU.";
      }
      enum "packet-loss-occurred-in-queue-on-fdr-module-of-lpu"{
        value 147202;
        description
          "Packet loss occurred in a queue on the FDR module of an LPU.";
      }
      enum "buffer-usage-of-sfu-is-high"{
        value 147203;
        description
          "The buffer usage of the SFU is high. Check its bandwidth.";
      }
      enum "all-links-on-sfu-are-down"{
        value 147204;
        description
          "All links on the SFU are down.";
      }
      enum "packet-loss-occurs-on-forward-engine-ingress-interface"{
        value 147205;
        description
          "Packet loss occurs on forward engine ingress interface.";
      }
      enum "link-access-to-forwarding-engine-is-abnormal"{
        value 147206;
        description
          "Link access to the forwarding engine is abnormal.";
      }
      enum "volume-of-forwarded-traffic-is-close-to-maximum-capability"{
        value 147207;
        description
          "The volume of forwarded traffic is close to the maximum forwarding capability of the device.";
      }
      enum "cpu-failed-to-send-packets"{
        value 147208;
        description
          "The CPU failed to send packets.";
      }
      enum "port-between-lsw-and-coprocessor-is-down"{
        value 147209;
        description
          "The port between LSW and Coprocessor is Down.";
      }
      enum "pll-status-unlocked-on-port-between-lsw-and-coprocessor"{
        value 147210;
        description
          "The PLL status is unlocked on the port between LSW and Coprocessor.";
      }
      enum "crc-error-packets-arise-on-port-between-lsw-and-coprocessor"{
        value 147211;
        description
          "CRC error packets are generated on the port between LSW and Coprocessor.";
      }
      enum "bandwidth-usage-of-internal-communication-interfaces-exceeded"{
        value 147212;
        description
          "The bandwidth usage of internal communication interfaces exceeded 80%.";
      }
      enum "packet-loss-occurred-on-internal-communication-interfaces"{
        value 147213;
        description
          "Packet loss occurred on internal communication interfaces.";
      }
      enum "bandwidth-of-links-between-sfu-and-lpu-was-insufficient"{
        value 147214;
        description
          "The bandwidth of links between an SFU and an LPU was insufficient.";
      }
      enum "access-to-forwarding-engine-is-unstable"{
        value 147215;
        description
          "Access to the forwarding engine is unstable.";
      }
    }
    description
      "This list contains the root reasons of the Huawei proprietary notifications.";
  }
  typedef loop-type {
    type enumeration {
      enum "no-loopback" {
        value 0;
        description
          "No loopback.";
      }
      enum "local" {
        value 1;
        description
          "Local loopback.";
      }
      enum "remote" {
        value 2;
        description
          "Remote loopback.";
      }
    }
    description
      "This object indicates the current interface status.";
  }
  typedef exception-type {
    type enumeration {
      enum "unknown" {
        value 0;
        description
          "Unknown.";
      }
      enum "rise-over" {
        value 1;
        description
          "Rise over threshold.";
      }
      enum "fall-below" {
        value 2;
        description
          "Fall below threshold.";
      }
    }
    description
      "The abnormal type for temperature, voltage, humidity.";
  }
  notification optical-remove {
    description
      "Optical module has been removed.";
    leaf entity-index {
      type uint32;
      description
        "Indicates the index of an entity.";
    }
    leaf entity-name {
      type string {
        length "0..255";
      }
      description
        "Indicates the name of an entity.";
    }
    leaf fault-id {
      type notification-probable-cause-type;
      description
        "Indicates the error code.";
    }
  }  
  notification optical-insert {
    description
      "Optical module has been inserted.";
    leaf entity-index {
      type uint32;
      description
        "Indicates the index of an entity.";
    }
    leaf entity-name {
      type string {
        length "0..255";
      }
      description
        "Indicates the name of an entity.";
    }
    leaf fault-id {
      type notification-probable-cause-type;
      description
        "Indicates the error code.";
    }
  }
  notification optical-unauthorized {
    description
      "The optical module was not certified by Huawei Ethernet Switch.";
    leaf entity-index {
      type uint32;
      description
        "Indicates the index of an entity.";
    }
    leaf entity-name {
      type string {
        length "0..255";
      }
      description
        "Indicates the name of an entity.";
    }
    leaf fault-id {
      type notification-probable-cause-type;
      description
        "Indicates the error code.";
    }
  }
  notification optical-unauthorized-resume {
    description
      "The alarm on optical module not certified by Huawei Ethernet Switch was clearned.";
    leaf entity-index {
      type uint32;
      description
        "Indicates the index of an entity.";
    }
    leaf entity-name {
      type string {
        length "0..255";
      }
      description
        "Indicates the name of an entity.";
    }
    leaf fault-id {
      type notification-probable-cause-type;
      description
        "Indicates the error code.";
    }
  }
  notification optical-invalid {
    description
      "Optical module is invalid.";
    leaf entity-index {
      type uint32;
      description
        "Indicates the index of an entity.";
    }
    leaf entity-name {
      type string {
        length "0..255";
      }
      description
        "Indicates the name of an entity.";
    }
    leaf fault-id {
      type notification-probable-cause-type;
      description
        "Indicates the error code.";
    }
  }
  notification optical-invalid-resume {
    description
      "Optical module resume from invalid situation.";
    leaf entity-index {
      type uint32;
      description
        "Indicates the index of an entity.";
    }
    leaf entity-name {
      type string {
        length "0..255";
      }
      description
        "Indicates the name of an entity.";
    }
    leaf fault-id {
      type notification-probable-cause-type;
      description
        "Indicates the error code.";
    }
  }
  notification card-remove {
    description
      "The card was removed.";
    leaf entity-index {
      type uint32;
      description
        "Indicates the index of an entity.";
    }
    leaf entity-name {
      type string {
        length "0..255";
      }
      description
        "Indicates the name of an entity.";
    }
    leaf entity-type {
      type notification-entity-type;
      description
        "Type of the notification entity. The value can be one of the following: - 1: MPU - 2: LPU - 3: SFU - 4: PIC - 5: CF card - 6: OFC.";
    }
    leaf fault-id {
      type notification-probable-cause-type;
      description
        "To describe the fault id of trap.";
    }
  }
  notification card-insert {
    description
      "The card was inserted.";
    leaf entity-index {
      type uint32;
      description
        "Indicates the index of an entity.";
    }
    leaf entity-name {
      type string {
        length "0..255";
      }
      description
        "Indicates the name of an entity.";
    }
    leaf entity-type {
      type notification-entity-type;
      description
        "Type of the notification entity. The value can be one of the following: - 1: MPU - 2: LPU - 3: SFU - 4: PIC - 5: CF card - 6: OFC.";
    }
    leaf fault-id {
      type notification-probable-cause-type;
      description
        "To describe the fault id of trap.";
    }
  }
  notification card-invalid {
    description
      "The card unavailable.";
    leaf entity-index {
      type uint32;
      description
        "Indicates the index of an entity.";
    }
    leaf entity-name {
      type string {
        length "0..255";
      }
      description
        "Indicates the name of an entity.";
    }
    leaf entity-type {
      type notification-entity-type;
      description
        "Type of the notification entity. The value can be one of the following: - 1: MPU - 2: LPU - 3: SFU - 4: PIC - 5: CF card - 6: OFC.";
    }
    leaf fault-id {
      type notification-probable-cause-type;
      description
        "Indicates the error code.";
    }
  }
  notification card-invalid-resume {
    description
      "The card resumed from unavailable.";
    leaf entity-index {
      type uint32;
      description
        "Indicates the index of an entity.";
    }
    leaf entity-name {
      type string {
        length "0..255";
      }
      description
        "Indicates the name of an entity.";
    }
    leaf entity-type {
      type notification-entity-type;
      description
        "Type of the notification entity. The value can be one of the following: - 1: MPU - 2: LPU - 3: SFU - 4: PIC - 5: CF card - 6: OFC.";
    }
    leaf fault-id {
      type notification-probable-cause-type;
      description
        "Indicates the error code.";
    }
  }
  notification card-fail {
    description
      "The card partially failed.";
    leaf entity-index {
      type uint32;
      description
        "Indicates the index of an entity.";
    }
    leaf entity-name {
      type string {
        length "0..255";
      }
      description
        "Indicates the name of an entity.";
    }
    leaf entity-type {
      type notification-entity-type;
      description
        "Type of the notification entity. The value can be one of the following: - 1: MPU - 2: LPU - 3: SFU - 4: PIC - 5: CF card - 6: OFC.";
    }
    leaf fault-id {
      type notification-probable-cause-type;
      description
        "Indicates the error code.";
    }
  }
  notification card-fail-resume {
    description
      "The card resumed from partial failure.";
    leaf entity-index {
      type uint32;
      description
        "Indicates the index of an entity.";
    }
    leaf entity-name {
      type string {
        length "0..255";
      }
      description
        "Indicates the name of an entity.";
    }
    leaf entity-type {
      type notification-entity-type;
      description
        "Type of the notification entity. The value can be one of the following: - 1: MPU - 2: LPU - 3: SFU - 4: PIC - 5: CF card - 6: OFC.";
    }
    leaf fault-id {
      type notification-probable-cause-type;
      description
        "Indicates the error code.";
    }
  }
  notification flow-control-pause-frame-abnormal {
    description
      "The port continuously received a large number of pause frames when it did not forward packets.";
    leaf entity-index {
      type uint32;
      description
        "Indicates the index of an entity.";
    }
    leaf entity-name {
      type string {
        length "0..255";
      }
      description
        "Indicates the name of an entity.";
    }
  }
  notification flow-control-pause-frame-abnormal-resume {
    description
      "The port recovered and did not receive pause frames.";
    leaf entity-index {
      type uint32;
      description
        "Indicates the index of an entity.";
    }
    leaf entity-name {
      type string {
        length "0..255";
      }
      description
        "Indicates the name of an entity.";
    }
  }
  notification au-hp {
    description
      "This object indicates that the administrative unit (AU) pointer in a higher order path (HP) indication signal alarm is generated.";
    leaf card-id {
      type uint32;
      description
        "Indicates the card ID.";
    }
    leaf hp-id {
      type uint32;
      description
        "Indicates the higher order path ID.";
    }
    leaf port-name {
      type string {
        length "1..32";
      }
      description
        "Indicates the physical port name.";
    }
    leaf port-id {
      type uint32;
      description
        "Indicates the port ID.";
    }
    leaf slot-id {
      type uint32;
      description
        "Indicates the slot ID.";
    }
  }
  notification au-hp-resume {
    description
      "This object indicates that the administrative unit (AU) pointer in the higher order path (HP) indication signal alarm is cleared.";
    leaf card-id {
      type uint32;
      description
        "Indicates the card ID.";
    }
    leaf hp-id {
      type uint32;
      description
        "Indicates the higher order path ID.";
    }
    leaf port-name {
      type string {
        length "1..32";
      }
      description
        "Indicates the physical port name.";
    }
    leaf port-id {
      type uint32;
      description
        "Indicates the port ID.";
    }
    leaf slot-id {
      type uint32;
      description
        "Indicates the slot ID.";
    }
  }
  notification b1-default-exceed {
    description
      "This object indicates that an alarm is generated when the number of B1 errors exceeds a specified threshold.";
    leaf card-id {
      type uint32;
      description
        "Indicates the card ID.";
    }
    leaf port-name {
      type string {
        length "1..32";
      }
      description
        "Indicates the physical port name.";
    }
    leaf port-id {
      type uint32;
      description
        "Indicates the port ID.";
    }
    leaf slot-id {
      type uint32;
      description
        "Indicates the slot ID.";
    }
  }
  notification b1-default-exceed-resume {
    description
      "This object indicates that a clear alarm is generated when the number of B1 errors falls below a specified threshold.";
    leaf card-id {
      type uint32;
      description
        "Indicates the card ID.";
    }
    leaf port-name {
      type string {
        length "1..32";
      }
      description
        "Indicates the physical port name.";
    }
    leaf port-id {
      type uint32;
      description
        "Indicates the port ID.";
    }
    leaf slot-id {
      type uint32;
      description
        "Indicates the slot ID.";
    }
  }
  notification bip2-default-exceed {
    description
      "This object indicates that an alarm is generated when the number of BIP2 errors exceeds a specified threshold.";
    leaf card-id {
      type uint32;
      description
        "Indicates the card ID.";
    }
    leaf hp-id {
      type uint32;
      description
        "Indicates the higher order path ID.";
    }
    leaf port-name {
      type string {
        length "1..32";
      }
      description
        "Indicates the physical port name.";
    }
    leaf lp-id {
      type uint32;
      description
        "Indicates the low order path ID.";
    }
    leaf port-id {
      type uint32;
      description
        "Indicates the port ID.";
    }
    leaf slot-id {
      type uint32;
      description
        "Indicates the slot ID.";
    }
  }
  notification bip2-default-exceed-resume {
    description
      "This object indicates that a clear alarm is generated when the number of BIP2 errors falls below a specified threshold.";
    leaf card-id {
      type uint32;
      description
        "Indicates the card ID.";
    }
    leaf hp-id {
      type uint32;
      description
        "Indicates the higher order path ID.";
    }
    leaf port-name {
      type string {
        length "1..32";
      }
      description
        "Indicates the physical port name.";
    }
    leaf lp-id {
      type uint32;
      description
        "Indicates the low order path ID.";
    }
    leaf port-id {
      type uint32;
      description
        "Indicates the port ID.";
    }
    leaf slot-id {
      type uint32;
      description
        "Indicates the slot ID.";
    }
  }
  notification b3-default-exceed {
    description
      "This object indicates that an alarm is generated when the number of B3 errors exceeds a specified threshold.";
    leaf card-id {
      type uint32;
      description
        "Indicates the card ID.";
    }
    leaf hp-id {
      type uint32;
      description
        "Indicates the higher order path ID.";
    }
    leaf port-name {
      type string {
        length "1..32";
      }
      description
        "Indicates the physical port name.";
    }
    leaf port-id {
      type uint32;
      description
        "Indicates the port ID.";
    }
    leaf slot-id {
      type uint32;
      description
        "Indicates the slot ID.";
    }
  }
  notification b3-default-exceed-resume {
    description
      "This object indicates that a clear alarm is generated when the number of B3 errors falls below a specified threshold.";
    leaf card-id {
      type uint32;
      description
        "Indicates the card ID.";
    }
    leaf hp-id {
      type uint32;
      description
        "Indicates the higher order path ID.";
    }
    leaf port-name {
      type string {
        length "1..32";
      }
      description
        "Indicates the physical port name.";
    }
    leaf port-id {
      type uint32;
      description
        "Indicates the port ID.";
    }
    leaf slot-id {
      type uint32;
      description
        "Indicates the slot ID.";
    }
  }
  notification channel-loopback {
    description
      "This object indicates that an alarm is generated when a channel loopback.";
    leaf hp-id {
      type uint32;
      description
        "Indicates the higher order path ID.";
    }
    leaf index {
      type uint32;
      description
        "Indicates the physical port index.";
    }
    leaf port-name {
      type string {
        length "1..32";
      }
      description
        "Indicates the physical port name.";
    }
    leaf loop-type {
      type loop-type;
      description
        "Type of the notification loop. The value can be one -of the following: - 0: stop-loopback - 1: local - 2: remote.";
    }
    leaf lp-id {
      type uint32;
      description
        "Indicates the lower order path ID.";
    }
  }
  notification channel-loopback-resume {
    description
      "This object indicates that a clear alarm is generated when a channel no loopback.";
    leaf hp-id {
      type uint32;
      description
        "Indicates the higher order path ID.";
    }
    leaf index {
      type uint32;
      description
        "Indicates the physical port index.";
    }
    leaf port-name {
      type string {
        length "1..32";
      }
      description
        "Indicates the physical port name.";
    }
    leaf loop-type {
      type loop-type;
      description
        "Type of the notification loop. The value can be one -of the following: - 0: stop-loopback - 1: local - 2: remote.";
    }
    leaf lp-id {
      type uint32;
      description
        "Indicates the lower order path ID.";
    }
  }
  notification cpos-e1-rai-signal {
    description
      "This object indicates that an RAI signal is generated on an E1 link channelized from VC12.";
    leaf card-id {
      type uint32;
      description
        "Indicates the card ID.";
    }
    leaf hp-id {
      type uint32;
      description
        "Indicates the higher order path ID.";
    }
    leaf port-name {
      type string {
        length "1..32";
      }
      description
        "Indicates the physical port name.";
    }
    leaf lp-id {
      type uint32;
      description
        "Indicates the low order path ID.";
    }
    leaf port-id {
      type uint32;
      description
        "Indicates the port ID.";
    }
    leaf slot-id {
      type uint32;
      description
        "Indicates the slot ID.";
    }
  }
  notification cpos-e1-rai-signal-resume {
    description
      "This object indicates that the RAI signal generated on an E1 link channelized from VC12 is cleared.";
    leaf card-id {
      type uint32;
      description
        "Indicates the card ID.";
    }
    leaf hp-id {
      type uint32;
      description
        "Indicates the higher order path ID.";
    }
    leaf port-name {
      type string {
        length "1..32";
      }
      description
        "Indicates the physical port name.";
    }
    leaf lp-id {
      type uint32;
      description
        "Indicates the low order path ID.";
    }
    leaf port-id {
      type uint32;
      description
        "Indicates the port ID.";
    }
    leaf slot-id {
      type uint32;
      description
        "Indicates the slot ID.";
    }
  }
  notification downstream-e1-cpos {
    description
      "This object indicates that a downstream alarm indication signal is generated on an E1 link channelized from VC12.";
    leaf card-id {
      type uint32;
      description
        "Indicates the card ID.";
    }
    leaf hp-id {
      type uint32;
      description
        "Indicates the higher order path ID.";
    }
    leaf port-name {
      type string {
        length "1..32";
      }
      description
        "Indicates the physical port name.";
    }
    leaf lp-id {
      type uint32;
      description
        "Indicates the low order path ID.";
    }
    leaf port-id {
      type uint32;
      description
        "Indicates the port ID.";
    }
    leaf slot-id {
      type uint32;
      description
        "Indicates the slot ID.";
    }
  }
  notification downstream-e1-cpos-resume {
    description
      "This object indicates that the downstream alarm indication signal generated on an E1 link channelized from VC12 is cleared.";
    leaf card-id {
      type uint32;
      description
        "Indicates the card ID.";
    }
    leaf hp-id {
      type uint32;
      description
        "Indicates the higher order path ID.";
    }
    leaf port-name {
      type string {
        length "1..32";
      }
      description
        "Indicates the physical port name.";
    }
    leaf lp-id {
      type uint32;
      description
        "Indicates the low order path ID.";
    }
    leaf port-id {
      type uint32;
      description
        "Indicates the port ID.";
    }
    leaf slot-id {
      type uint32;
      description
        "Indicates the slot ID.";
    }
  }
  notification loss-of-frame-e1-cpos {
    description
      "This object indicates that an out of frame (OOF) alarm is generated on the framed E1 channelized from VC12.";
    leaf card-id {
      type uint32;
      description
        "Indicates the card ID.";
    }
    leaf hp-id {
      type uint32;
      description
        "Indicates the higher order path ID.";
    }
    leaf port-name {
      type string {
        length "1..32";
      }
      description
        "Indicates the physical port name.";
    }
    leaf lp-id {
      type uint32;
      description
        "Indicates the low order path ID.";
    }
    leaf port-id {
      type uint32;
      description
        "Indicates the port ID.";
    }
    leaf slot-id {
      type uint32;
      description
        "Indicates the slot ID.";
    }
  }
  notification loss-of-frame-e1-cpos-resume {
    description
      "This object indicates that the OOF alarm generated on the framed E1 channelized from VC12 is cleared.";
    leaf card-id {
      type uint32;
      description
        "Indicates the card ID.";
    }
    leaf hp-id {
      type uint32;
      description
        "Indicates the higher order path ID.";
    }
    leaf port-name {
      type string {
        length "1..32";
      }
      description
        "Indicates the physical port name.";
    }
    leaf lp-id {
      type uint32;
      description
        "Indicates the low order path ID.";
    }
    leaf port-id {
      type uint32;
      description
        "Indicates the port ID.";
    }
    leaf slot-id {
      type uint32;
      description
        "Indicates the slot ID.";
    }
  }
  notification loss-multiframe-e1-cpos {
    description
      "This object indicates that an out of multiframe (OOM) alarm is generated on the framed E1 channelized from VC12.";
    leaf card-id {
      type uint32;
      description
        "Indicates the card ID.";
    }
    leaf hp-id {
      type uint32;
      description
        "Indicates the higher order path ID.";
    }
    leaf lp-id {
      type uint32;
      description
        "Indicates the lower order path ID.";
    }
    leaf port-name {
      type string {
        length "1..32";
      }
      description
        "Indicates the physical port name.";
    }
    leaf port-id {
      type uint32;
      description
        "Indicates the port ID.";
    }
    leaf slot-id {
      type uint32;
      description
        "Indicates the slot ID.";
    }
  }
  notification loss-multiframe-e1-cpos-resume {
    description
      "This object indicates that the OOM alarm generated on the framed E1 channelized from VC12 is cleared.";
    leaf card-id {
      type uint32;
      description
        "Indicates the card ID.";
    }
    leaf hp-id {
      type uint32;
      description
        "Indicates the higher order path ID.";
    }
    leaf lp-id {
      type uint32;
      description
        "Indicates the lower order path ID.";
    }
    leaf port-name {
      type string {
        length "1..32";
      }
      description
        "Indicates the physical port name.";
    }
    leaf port-id {
      type uint32;
      description
        "Indicates the port ID.";
    }
    leaf slot-id {
      type uint32;
      description
        "Indicates the slot ID.";
    }
  }
  notification upstream-e1-cpos {
    description
      "This object indicates that an upstream alarm indication signal is generated on an E1 link channelized from VC12.";
    leaf card-id {
      type uint32;
      description
        "Indicates the card ID.";
    }
    leaf hp-id {
      type uint32;
      description
        "Indicates the higher order path ID.";
    }
    leaf port-name {
      type string {
        length "1..32";
      }
      description
        "Indicates the physical port name.";
    }
    leaf lp-id {
      type uint32;
      description
        "Indicates the low order path ID.";
    }
    leaf port-id {
      type uint32;
      description
        "Indicates the port ID.";
    }
    leaf slot-id {
      type uint32;
      description
        "Indicates the slot ID.";
    }
  }
  notification upstream-e1-cpos-resume {
    description
      "This object indicates that an upstream alarm indication signal generated on an E1 link channelized from VC12 is cleared.";
    leaf card-id {
      type uint32;
      description
        "Indicates the card ID.";
    }
    leaf hp-id {
      type uint32;
      description
        "Indicates the higher order path ID.";
    }
    leaf port-name {
      type string {
        length "1..32";
      }
      description
        "Indicates the physical port name.";
    }
    leaf lp-id {
      type uint32;
      description
        "Indicates the low order path ID.";
    }
    leaf port-id {
      type uint32;
      description
        "Indicates the port ID.";
    }
    leaf slot-id {
      type uint32;
      description
        "Indicates the slot ID.";
    }
  }
  notification remote-indication-e1 {
    description
      "This object indicates that a remote alarm indication (RAI) signal is generated on an E1 link.";
    leaf card-id {
      type uint32;
      description
        "Indicates the card ID.";
    }
    leaf port-name {
      type string {
        length "1..32";
      }
      description
        "Indicates the physical port name.";
    }
    leaf port-id {
      type uint32;
      description
        "Indicates the port ID.";
    }
    leaf slot-id {
      type uint32;
      description
        "Indicates the slot ID.";
    }
  }
  notification remote-indication-e1-resume {
    description
      "This object indicates that the RAI signal generated on an E1 link is cleared.";
    leaf card-id {
      type uint32;
      description
        "Indicates the card ID.";
    }
    leaf port-name {
      type string {
        length "1..32";
      }
      description
        "Indicates the physical port name.";
    }
    leaf port-id {
      type uint32;
      description
        "Indicates the port ID.";
    }
    leaf slot-id {
      type uint32;
      description
        "Indicates the slot ID.";
    }
  }
  notification downstream-e1 {
    description
      "This object indicates that a downstream alarm indication signal is generated on an E1 interface.";
    leaf card-id {
      type uint32;
      description
        "Indicates the card ID.";
    }
    leaf port-name {
      type string {
        length "1..32";
      }
      description
        "Indicates the physical port name.";
    }
    leaf port-id {
      type uint32;
      description
        "Indicates the port ID.";
    }
    leaf slot-id {
      type uint32;
      description
        "Indicates the slot ID.";
    }
  }
  notification downstream-e1-resume {
    description
      "This object indicates that the downstream alarm indication signal generated on an E1 interface is cleared.";
    leaf card-id {
      type uint32;
      description
        "Indicates the card ID.";
    }
    leaf port-name {
      type string {
        length "1..32";
      }
      description
        "Indicates the physical port name.";
    }
    leaf port-id {
      type uint32;
      description
        "Indicates the port ID.";
    }
    leaf slot-id {
      type uint32;
      description
        "Indicates the slot ID.";
    }
  }
  notification errored-second-exceed {
    description
      "This object indicates that the number of errored seconds exceeds a specified threshold.";
    leaf card-id {
      type uint32;
      description
        "Indicates the card ID.";
    }
    leaf port-name {
      type string {
        length "1..32";
      }
      description
        "Indicates the physical port name.";
    }
    leaf port-id {
      type uint32;
      description
        "Indicates the port ID.";
    }
    leaf slot-id {
      type uint32;
      description
        "Indicates the slot ID.";
    }
  }
  notification errored-second-exceed-resume {
    description
      "This object indicates that the number of errored seconds falls below a specified threshold.";
    leaf card-id {
      type uint32;
      description
        "Indicates the card ID.";
    }
    leaf port-name {
      type string {
        length "1..32";
      }
      description
        "Indicates the physical port name.";
    }
    leaf port-id {
      type uint32;
      description
        "Indicates the port ID.";
    }
    leaf slot-id {
      type uint32;
      description
        "Indicates the slot ID.";
    }
  }
  notification loss-multiframe-e1 {
    description
      "This object indicates an LOM alarm on the framed E1.";
    leaf card-id {
      type uint32;
      description
        "Indicates the card ID.";
    }
    leaf port-name {
      type string {
        length "1..32";
      }
      description
        "Indicates the physical port name.";
    }
    leaf port-id {
      type uint32;
      description
        "Indicates the port ID.";
    }
    leaf slot-id {
      type uint32;
      description
        "Indicates the slot ID.";
    }
  }
  notification loss-multiframe-e1-resume {
    description
      "This object indicates that the LOM alarm on the framed E1 is cleared.";
    leaf card-id {
      type uint32;
      description
        "Indicates the card ID.";
    }
    leaf port-name {
      type string {
        length "1..32";
      }
      description
        "Indicates the physical port name.";
    }
    leaf port-id {
      type uint32;
      description
        "Indicates the port ID.";
    }
    leaf slot-id {
      type uint32;
      description
        "Indicates the slot ID.";
    }
  }
  notification upstream-e1 {
    description
      "This object indicates that an upstream alarm indication signal is generated on an E1 interface.";
    leaf card-id {
      type uint32;
      description
        "Indicates the card ID.";
    }
    leaf port-name {
      type string {
        length "1..32";
      }
      description
        "Indicates the physical port name.";
    }
    leaf port-id {
      type uint32;
      description
        "Indicates the port ID.";
    }
    leaf slot-id {
      type uint32;
      description
        "Indicates the slot ID.";
    }
  }
  notification upstream-e1-resume {
    description
      "This object indicates that the upstream alarm indication signal generated on an E1 interface is cleared.";
    leaf card-id {
      type uint32;
      description
        "Indicates the card ID.";
    }
    leaf port-name {
      type string {
        length "1..32";
      }
      description
        "Indicates the physical port name.";
    }
    leaf port-id {
      type uint32;
      description
        "Indicates the port ID.";
    }
    leaf slot-id {
      type uint32;
      description
        "Indicates the slot ID.";
    }
  }
  notification remote-e3 {
    description
      "Indicates the alarm is detected.";
    leaf card-id {
      type uint32;
      description
        "Indicates the card ID.";
    }
    leaf port-name {
      type string {
        length "1..32";
      }
      description
        "Indicates the physical port name.";
    }
    leaf port-id {
      type uint32;
      description
        "Indicates the port ID.";
    }
    leaf slot-id {
      type uint32;
      description
        "Indicates the slot ID.";
    }
  }
  notification remote-e3-resume {
    description
      "Indicates the alarm is cleared.";
    leaf card-id {
      type uint32;
      description
        "Indicates the card ID.";
    }
    leaf port-name {
      type string {
        length "1..32";
      }
      description
        "Indicates the physical port name.";
    }
    leaf port-id {
      type uint32;
      description
        "Indicates the port ID.";
    }
    leaf slot-id {
      type uint32;
      description
        "Indicates the slot ID.";
    }
  }
  notification upstream-e3 {
    description
      "Indicates the alarm is detected.";
    leaf card-id {
      type uint32;
      description
        "Indicates the card ID.";
    }
    leaf port-name {
      type string {
        length "1..32";
      }
      description
        "Indicates the physical port name.";
    }
    leaf port-id {
      type uint32;
      description
        "Indicates the port ID.";
    }
    leaf slot-id {
      type uint32;
      description
        "Indicates the slot ID.";
    }
  }
  notification upstream-e3-resume {
    description
      "Indicates the alarm is cleared.";
    leaf card-id {
      type uint32;
      description
        "Indicates the card ID.";
    }
    leaf port-name {
      type string {
        length "1..32";
      }
      description
        "Indicates the physical port name.";
    }
    leaf port-id {
      type uint32;
      description
        "Indicates the port ID.";
    }
    leaf slot-id {
      type uint32;
      description
        "Indicates the slot ID.";
    }
  }
  notification j0-trace-mismatch {
    description
      "This object indicates that an alarm for trace j0 identifier mismatch is generated.";
    leaf card-id {
      type uint32;
      description
        "Indicates the card ID.";
    }
    leaf port-name {
      type string {
        length "1..32";
      }
      description
        "Indicates the physical port name.";
    }
    leaf port-id {
      type uint32;
      description
        "Indicates the port ID.";
    }
    leaf slot-id {
      type uint32;
      description
        "Indicates the slot ID.";
    }
  }
  notification j0-trace-mismatch-resume {
    description
      "This object indicates that the alarm for j0 trace identifier mismatch is cleared.";
    leaf card-id {
      type uint32;
      description
        "Indicates the card ID.";
    }
    leaf port-name {
      type string {
        length "1..32";
      }
      description
        "Indicates the physical port name.";
    }
    leaf port-id {
      type uint32;
      description
        "Indicates the port ID.";
    }
    leaf slot-id {
      type uint32;
      description
        "Indicates the slot ID.";
    }
  }
  notification signal-mismatch-lp {
    description
      "This object indicates a lower order path (LP) signal label mismatch alarm.";
    leaf card-id {
      type uint32;
      description
        "Indicates the card ID.";
    }
    leaf hp-id {
      type uint32;
      description
        "Indicates the higher order path ID.";
    }
    leaf port-name {
      type string {
        length "1..32";
      }
      description
        "Indicates the physical port name.";
    }
    leaf lp-id {
      type uint32;
      description
        "Indicates the low order path ID.";
    }
    leaf port-id {
      type uint32;
      description
        "Indicates the port ID.";
    }
    leaf slot-id {
      type uint32;
      description
        "Indicates the slot ID.";
    }
  }
  notification signal-mismatch-lp-resume {
    description
      "This object indicates that the lower order path (LP) signal label mismatch alarm is cleared.";
    leaf card-id {
      type uint32;
      description
        "Indicates the card ID.";
    }
    leaf hp-id {
      type uint32;
      description
        "Indicates the higher order path ID.";
    }
    leaf port-name {
      type string {
        length "1..32";
      }
      description
        "Indicates the physical port name.";
    }
    leaf lp-id {
      type uint32;
      description
        "Indicates the low order path ID.";
    }
    leaf port-id {
      type uint32;
      description
        "Indicates the port ID.";
    }
    leaf slot-id {
      type uint32;
      description
        "Indicates the slot ID.";
    }
  }
  notification trace-mismatch-lp {
    description
      "This object indicates that signal label mismatch alarm on VC12 lower order path alarm.";
    leaf card-id {
      type uint32;
      description
        "Indicates the card ID.";
    }
    leaf hp-id {
      type uint32;
      description
        "Indicates the higher order path ID.";
    }
    leaf port-name {
      type string {
        length "1..32";
      }
      description
        "Indicates the physical port name.";
    }
    leaf lp-id {
      type uint32;
      description
        "Indicates the low order path ID.";
    }
    leaf port-id {
      type uint32;
      description
        "Indicates the port ID.";
    }
    leaf slot-id {
      type uint32;
      description
        "Indicates the slot ID.";
    }
  }
  notification trace-mismatch-lp-resume {
    description
      "This object indicates that signal label mismatch alarm on VC12 lower order path alarm is cleared.";
    leaf card-id {
      type uint32;
      description
        "Indicates the card ID.";
    }
    leaf hp-id {
      type uint32;
      description
        "Indicates the higher order path ID.";
    }
    leaf port-name {
      type string {
        length "1..32";
      }
      description
        "Indicates the physical port name.";
    }
    leaf lp-id {
      type uint32;
      description
        "Indicates the low order path ID.";
    }
    leaf port-id {
      type uint32;
      description
        "Indicates the port ID.";
    }
    leaf slot-id {
      type uint32;
      description
        "Indicates the slot ID.";
    }
  }
  notification unequipped-lp {
    description
      "This object indicates that a lower order path (LP) unequipped indication signal (PUNEQ) alarm is generated.";
    leaf card-id {
      type uint32;
      description
        "Indicates the card ID.";
    }
    leaf hp-id {
      type uint32;
      description
        "Indicates the higher order path ID.";
    }
    leaf port-name {
      type string {
        length "1..32";
      }
      description
        "Indicates the physical port name.";
    }
    leaf lp-id {
      type uint32;
      description
        "Indicates the low order path ID.";
    }
    leaf port-id {
      type uint32;
      description
        "Indicates the port ID.";
    }
    leaf slot-id {
      type uint32;
      description
        "Indicates the slot ID.";
    }
  }
  notification unequipped-lp-resume {
    description
      "This object indicates that a lower order path (LP) unequipped indication signal (PUNEQ) alarm is cleard.";
    leaf card-id {
      type uint32;
      description
        "Indicates the card ID.";
    }
    leaf hp-id {
      type uint32;
      description
        "Indicates the higher order path ID.";
    }
    leaf port-name {
      type string {
        length "1..32";
      }
      description
        "Indicates the physical port name.";
    }
    leaf lp-id {
      type uint32;
      description
        "Indicates the low order path ID.";
    }
    leaf port-id {
      type uint32;
      description
        "Indicates the port ID.";
    }
    leaf slot-id {
      type uint32;
      description
        "Indicates the slot ID.";
    }
  }
  notification out-of-lock-clock {
    description
      "This object indicates that an alarm is generated when out of lock of received reference clock.";
    leaf card-id {
      type uint32;
      description
        "Indicates the card ID.";
    }
    leaf port-name {
      type string {
        length "1..32";
      }
      description
        "Indicates the physical port name.";
    }
    leaf port-id {
      type uint32;
      description
        "Indicates the port ID.";
    }
    leaf slot-id {
      type uint32;
      description
        "Indicates the slot ID.";
    }
  }
  notification out-of-lock-clock-resume {
    description
      "This object indicates that a clear alarm is generated when there is a clock on the receive line.";
    leaf card-id {
      type uint32;
      description
        "Indicates the card ID.";
    }
    leaf port-name {
      type string {
        length "1..32";
      }
      description
        "Indicates the physical port name.";
    }
    leaf port-id {
      type uint32;
      description
        "Indicates the port ID.";
    }
    leaf slot-id {
      type uint32;
      description
        "Indicates the slot ID.";
    }
  }
  notification tributary-unit-lp {
    description
      "This object indicates the lower order path (LP) tributary unit (TU) alarm indication.";
    leaf card-id {
      type uint32;
      description
        "Indicates the card ID.";
    }
    leaf hp-id {
      type uint32;
      description
        "Indicates the higher order path ID.";
    }
    leaf port-name {
      type string {
        length "1..32";
      }
      description
        "Indicates the physical port name.";
    }
    leaf lp-id {
      type uint32;
      description
        "Indicates the low order path ID.";
    }
    leaf port-id {
      type uint32;
      description
        "Indicates the port ID.";
    }
    leaf slot-id {
      type uint32;
      description
        "Indicates the slot ID.";
    }
  }
  notification tributary-unit-lp-resume {
    description
      "This object indicates that the lower order path (LP) tributary unit (TU) alarm is cleared.";
    leaf card-id {
      type uint32;
      description
        "Indicates the card ID.";
    }
    leaf hp-id {
      type uint32;
      description
        "Indicates the higher order path ID.";
    }
    leaf port-name {
      type string {
        length "1..32";
      }
      description
        "Indicates the physical port name.";
    }
    leaf lp-id {
      type uint32;
      description
        "Indicates the low order path ID.";
    }
    leaf port-id {
      type uint32;
      description
        "Indicates the port ID.";
    }
    leaf slot-id {
      type uint32;
      description
        "Indicates the slot ID.";
    }
  }
  notification v5-virtual-container {
    description
      "This object indicates that an alarm indication signal is generated in the virtual container.";
    leaf card-id {
      type uint32;
      description
        "Indicates the card ID.";
    }
    leaf hp-id {
      type uint32;
      description
        "Indicates the higher order path ID.";
    }
    leaf port-name {
      type string {
        length "1..32";
      }
      description
        "Indicates the physical port name.";
    }
    leaf lp-id {
      type uint32;
      description
        "Indicates the low order path ID.";
    }
    leaf port-id {
      type uint32;
      description
        "Indicates the port ID.";
    }
    leaf slot-id {
      type uint32;
      description
        "Indicates the slot ID.";
    }
  }
  notification v5-virtual-container-resume {
    description
      "This object indicates that the alarm indication signal generated in the virtual container is cleared.";
    leaf card-id {
      type uint32;
      description
        "Indicates the card ID.";
    }
    leaf hp-id {
      type uint32;
      description
        "Indicates the higher order path ID.";
    }
    leaf port-name {
      type string {
        length "1..32";
      }
      description
        "Indicates the physical port name.";
    }
    leaf lp-id {
      type uint32;
      description
        "Indicates the low order path ID.";
    }
    leaf port-id {
      type uint32;
      description
        "Indicates the port ID.";
    }
    leaf slot-id {
      type uint32;
      description
        "Indicates the slot ID.";
    }
  }
  notification loss-au-lp {
    description
      "This object indicates that an alarm is generated when the administrative unit (AU) pointer in the lower order path (LP) is lost.";
    leaf card-id {
      type uint32;
      description
        "Indicates the card ID.";
    }
    leaf hp-id {
      type uint32;
      description
        "Indicates the higher order path ID.";
    }
    leaf port-name {
      type string {
        length "1..32";
      }
      description
        "Indicates the physical port name.";
    }
    leaf lp-id {
      type uint32;
      description
        "Indicates the low order path ID.";
    }
    leaf port-id {
      type uint32;
      description
        "Indicates the port ID.";
    }
    leaf slot-id {
      type uint32;
      description
        "Indicates the slot ID.";
    }
  }
  notification loss-au-lp-resume {
    description
      "This object indicates that the alarm generated due to the loss of the AU pointer in the lower order path (LP) is cleared.";
    leaf card-id {
      type uint32;
      description
        "Indicates the card ID.";
    }
    leaf hp-id {
      type uint32;
      description
        "Indicates the higher order path ID.";
    }
    leaf port-name {
      type string {
        length "1..32";
      }
      description
        "Indicates the physical port name.";
    }
    leaf lp-id {
      type uint32;
      description
        "Indicates the low order path ID.";
    }
    leaf port-id {
      type uint32;
      description
        "Indicates the port ID.";
    }
    leaf slot-id {
      type uint32;
      description
        "Indicates the slot ID.";
    }
  }
  notification remote-defect-lp {
    description
      "This object indicates that a lower order path (LP) remote defect indication (PRDI) alarm is generated.";
    leaf card-id {
      type uint32;
      description
        "Indicates the card ID.";
    }
    leaf hp-id {
      type uint32;
      description
        "Indicates the higher order path ID.";
    }
    leaf port-name {
      type string {
        length "1..32";
      }
      description
        "Indicates the physical port name.";
    }
    leaf lp-id {
      type uint32;
      description
        "Indicates the low order path ID.";
    }
    leaf port-id {
      type uint32;
      description
        "Indicates the port ID.";
    }
    leaf slot-id {
      type uint32;
      description
        "Indicates the slot ID.";
    }
  }
  notification remote-defect-lp-resume {
    description
      "This object indicates that a lower order path (LP) remote defect indication (PRDI) alarm is cleared.";
    leaf card-id {
      type uint32;
      description
        "Indicates the card ID.";
    }
    leaf hp-id {
      type uint32;
      description
        "Indicates the higher order path ID.";
    }
    leaf port-name {
      type string {
        length "1..32";
      }
      description
        "Indicates the physical port name.";
    }
    leaf lp-id {
      type uint32;
      description
        "Indicates the low order path ID.";
    }
    leaf port-id {
      type uint32;
      description
        "Indicates the port ID.";
    }
    leaf slot-id {
      type uint32;
      description
        "Indicates the slot ID.";
    }
  }
  notification remote-failure-lp {
    description
      "This object indicates that an alarm is generated when a lower order path (LP) remote failure indication (RFI) signal is detected.";
    leaf card-id {
      type uint32;
      description
        "Indicates the card ID.";
    }
    leaf hp-id {
      type uint32;
      description
        "Indicates the higher order path ID.";
    }
    leaf port-name {
      type string {
        length "1..32";
      }
      description
        "Indicates the physical port name.";
    }
    leaf lp-id {
      type uint32;
      description
        "Indicates the low order path ID.";
    }
    leaf port-id {
      type uint32;
      description
        "Indicates the port ID.";
    }
    leaf slot-id {
      type uint32;
      description
        "Indicates the slot ID.";
    }
  }
  notification remote-failure-lp-resume {
    description
      "This object indicates that a clear alarm is generated when the lower order path (LP) remote failure indication (RFI) signal is cleared.";
    leaf card-id {
      type uint32;
      description
        "Indicates the card ID.";
    }
    leaf hp-id {
      type uint32;
      description
        "Indicates the higher order path ID.";
    }
    leaf port-name {
      type string {
        length "1..32";
      }
      description
        "Indicates the physical port name.";
    }
    leaf lp-id {
      type uint32;
      description
        "Indicates the low order path ID.";
    }
    leaf port-id {
      type uint32;
      description
        "Indicates the port ID.";
    }
    leaf slot-id {
      type uint32;
      description
        "Indicates the slot ID.";
    }
  }
  notification port-license-act-fail {
    description
      "This object indicates that the license for a physical port fails to be activated.";
    leaf item-name {
      type string {
        length "1..32";
      }
      description
        "Item name.";
    }
    leaf physical-index {
      type uint32;
      description
        "Indicates the physical port index.";
    }
    leaf port-name {
      type string {
        length "1..32";
      }
      description
        "Indicates the physical port name.";
    }
  }
  notification port-license-act-success {
    description
      "This object indicates that the license for a physical port is successfully activated.";
    leaf item-name {
      type string {
        length "1..32";
      }
      description
        "Item name.";
    }
    leaf physical-index {
      type uint32;
      description
        "Indicates the physical port index.";
    }
    leaf port-name {
      type string {
        length "1..32";
      }
      description
        "Indicates the physical port name.";
    }
  }
  notification resource-dead-line {
    description
      "Port authorization grace period alarm.";
    leaf gtl-remain-time {
      type uint32;
      description
        "Gtl remain time.";
    }
    leaf physical-index {
      type uint32;
      description
        "Indicates the physical port index.";
    }
    leaf port-name {
      type string {
        length "1..32";
      }
      description
        "Indicates the physical port name.";
    }
  }
  notification resource-dead-line-resume {
    description
      "Port authorization grace period alarm resume.";
    leaf gtl-remain-time {
      type uint32;
      description
        "Gtl remain time.";
    }
    leaf physical-index {
      type uint32;
      description
        "Indicates the physical port index.";
    }
    leaf port-name {
      type string {
        length "1..32";
      }
      description
        "Indicates the physical port name.";
    }
  }
  notification upstream-pcm {
    description
      "Upstream signals were abnormal.";
    leaf physical-port-index {
      type uint32;
      description
        "Indicates the physical port index.";
    }
    leaf port-name {
      type string {
        length "1..32";
      }
      description
        "Indicates the physical port name.";
    }
  }
  notification upstream-pcm-resume {
    description
      "Upstream signals recovered.";
    leaf physical-port-index {
      type uint32;
      description
        "Indicates the physical port index.";
    }
    leaf port-name {
      type string {
        length "1..32";
      }
      description
        "Indicates the physical port name.";
    }
  }
  notification au-pointer-loss-lp {
    description
      "This object indicates the loss of the AU pointer in a higher order path (HP) indication signal alarm is generated.";
    leaf card-id {
      type uint32;
      description
        "Indicates the card ID.";
    }
    leaf port-name {
      type string {
        length "1..32";
      }
      description
        "Indicates the physical port name.";
    }
    leaf port-id {
      type uint32;
      description
        "Indicates the port ID.";
    }
    leaf slot-id {
      type uint32;
      description
        "Indicates the slot ID.";
    }
  }
  notification au-pointer-loss-lp-resume {
    description
      "This object indicates the loss of the AU pointer in a higher order path (HP) indication signal alarm is cleard.";
    leaf card-id {
      type uint32;
      description
        "Indicates the card ID.";
    }
    leaf port-name {
      type string {
        length "1..32";
      }
      description
        "Indicates the physical port name.";
    }
    leaf port-id {
      type uint32;
      description
        "Indicates the port ID.";
    }
    leaf slot-id {
      type uint32;
      description
        "Indicates the slot ID.";
    }
  }
  notification b1-configured-exceed {
    description
      "This object indicates that the number of error bits for the B1 RS exceeds a configured threshold.";
    leaf card-id {
      type uint32;
      description
        "Indicates the card ID.";
    }
    leaf port-name {
      type string {
        length "1..32";
      }
      description
        "Indicates the physical port name.";
    }
    leaf port-id {
      type uint32;
      description
        "Indicates the port ID.";
    }
    leaf slot-id {
      type uint32;
      description
        "Indicates the slot ID.";
    }
  }
  notification b1-configured-exceed-resume {
    description
      "This object indicates that the number of error bits for the B1 RS falls below the configured threshold.";
    leaf card-id {
      type uint32;
      description
        "Indicates the card ID.";
    }
    leaf port-name {
      type string {
        length "1..32";
      }
      description
        "Indicates the physical port name.";
    }
    leaf port-id {
      type uint32;
      description
        "Indicates the port ID.";
    }
    leaf slot-id {
      type uint32;
      description
        "Indicates the slot ID.";
    }
  }
  notification b2-configured-exceed {
    description
      "This object indicates that the number of error bits for the B2 exceeds a configured threshold.";
    leaf card-id {
      type uint32;
      description
        "Indicates the card ID.";
    }
    leaf port-name {
      type string {
        length "1..32";
      }
      description
        "Indicates the physical port name.";
    }
    leaf port-id {
      type uint32;
      description
        "Indicates the port ID.";
    }
    leaf slot-id {
      type uint32;
      description
        "Indicates the slot ID.";
    }
  }
  notification b2-configured-exceed-resume {
    description
      "This object indicates that the number of error bits for the B2 falls below the configured threshold.";
    leaf card-id {
      type uint32;
      description
        "Indicates the card ID.";
    }
    leaf port-name {
      type string {
        length "1..32";
      }
      description
        "Indicates the physical port name.";
    }
    leaf port-id {
      type uint32;
      description
        "Indicates the port ID.";
    }
    leaf slot-id {
      type uint32;
      description
        "Indicates the slot ID.";
    }
  }
  notification b3-configured-exceed {
    description
      "This object indicates that the number of bit errors on the B3 exceeds the configured threshold.";
    leaf card-id {
      type uint32;
      description
        "Indicates the card ID.";
    }
    leaf port-name {
      type string {
        length "1..32";
      }
      description
        "Indicates the physical port name.";
    }
    leaf port-id {
      type uint32;
      description
        "Indicates the port ID.";
    }
    leaf slot-id {
      type uint32;
      description
        "Indicates the slot ID.";
    }
    leaf hp-id {
      type uint32;
      description
        "Indicates the higher order path ID.";
    }
  }
  notification b3-configured-exceed-resume {
    description
      "This object indicates that the number of bit errors on the B3 falls below the configured threshold.";
    leaf card-id {
      type uint32;
      description
        "Indicates the card ID.";
    }
    leaf port-name {
      type string {
        length "1..32";
      }
      description
        "Indicates the physical port name.";
    }
    leaf port-id {
      type uint32;
      description
        "Indicates the port ID.";
    }
    leaf slot-id {
      type uint32;
      description
        "Indicates the slot ID.";
    }
    leaf hp-id {
      type uint32;
      description
        "Indicates the higher order path ID.";
    }
  }
  notification fog-abnormal {
    description
      "Fog rise over alarm threshold.";
    leaf exception-type {
      type exception-type;
      description
        "Type of the notification entity threshold.";
    }
    leaf threshold {
      type uint32;
      description
        "The threshold value of temperature, humidity, fog......";
    }
    leaf current {
      type uint32;
      description
        "The current value that been measured.";
    }
    leaf fault-code {
      type notification-probable-cause-type;
      description
        "To describe the fault id of trap.";
    }
  }
  notification fog-abnormal-resume {
    description
      "Fog back to normal level.";
    leaf exception-type {
      type exception-type;
      description
        "Type of the notification entity threshold.";
    }
    leaf threshold {
      type uint32;
      description
        "The threshold value of temperature, humidity, fog......";
    }
    leaf current {
      type uint32;
      description
        "The current value that been measured.";
    }
    leaf fault-code {
      type notification-probable-cause-type;
      description
        "To describe the fault id of trap.";
    }
  }
  notification gate-abnormal {
    description
      "Gate switch to the alarm status.";
    leaf exception-type {
      type exception-type;
      description
        "Type of the notification entity threshold.";
    }
    leaf threshold {
      type uint32;
      description
        "The threshold value of temperature, humidity, fog......";
    }
    leaf current {
      type uint32;
      description
        "The current value that been measured.";
    }
    leaf fault-code {
      type notification-probable-cause-type;
      description
        "To describe the fault id of trap.";
    }
  }
  notification gate-abnormal-resume {
    description
      "Gate switch to normal status.";
    leaf exception-type {
      type exception-type;
      description
        "Type of the notification entity threshold.";
    }
    leaf threshold {
      type uint32;
      description
        "The threshold value of temperature, humidity, fog......";
    }
    leaf current {
      type uint32;
      description
        "The current value that been measured.";
    }
    leaf fault-code {
      type notification-probable-cause-type;
      description
        "To describe the fault id of trap.";
    }
  }
  notification gps-module-insert {
    description
      "The gps module was inserted.";
    leaf entity-physical-index {
      type uint32;
      description
        "The index of physical.";
    }
    leaf port-name {
      type string {
        length "1..32";
      }
      description
        "Entity physical name.";
    }
  }
  notification gps-module-remove {
    description
      "The gps module was removed.";
    leaf entity-physical-index {
      type uint32;
      description
        "The index of physical.";
    }
    leaf port-name {
      type string {
        length "1..32";
      }
      description
        "Entity physical name.";
    }
  }
  notification trace-unstable-lp {
    description
      "This object indicates that an alarm is generated when the higher order path (HP) trace identifier is unstable.";
    leaf card-id {
      type uint32;
      description
        "Indicates the card ID.";
    }
    leaf hp-id {
      type uint32;
      description
        "Indicates the higher order path ID.";
    }
    leaf port-name {
      type string {
        length "1..32";
      }
      description
        "Indicates the physical port name.";
    }
    leaf port-id {
      type uint32;
      description
        "Indicates the port ID.";
    }
    leaf slot-id {
      type uint32;
      description
        "Indicates the slot ID.";
    }
  }
  notification trace-unstable-lp-resume {
    description
      "This object indicates that a clear alarm is generated when the higher order path (HP) trace identifier becomes stable.";
    leaf card-id {
      type uint32;
      description
        "Indicates the card ID.";
    }
    leaf hp-id {
      type uint32;
      description
        "Indicates the higher order path ID.";
    }
    leaf port-name {
      type string {
        length "1..32";
      }
      description
        "Indicates the physical port name.";
    }
    leaf port-id {
      type uint32;
      description
        "Indicates the port ID.";
    }
    leaf slot-id {
      type uint32;
      description
        "Indicates the slot ID.";
    }
  }
  notification humidity-abnormal {
    description
      "Humidity rise over or fall below the alarm threshold.";
    leaf exception-type {
      type exception-type;
      description
        "Type of the notification entity threshold.";
    }
    leaf threshold {
      type uint32;
      description
        "The threshold value of temperature, humidity, fog......";
    }
    leaf current {
      type uint32;
      description
        "The current value that been measured.";
    }
    leaf fault-code {
      type notification-probable-cause-type;
      description
        "To describe the fault id of trap.";
    }
  }
  notification humidity-abnormal-resume {
    description
      "Humidity back to normal level.";
    leaf exception-type {
      type exception-type;
      description
        "Type of the notification entity threshold.";
    }
    leaf threshold {
      type uint32;
      description
        "The threshold value of temperature, humidity, fog......";
    }
    leaf current {
      type uint32;
      description
        "The current value that been measured.";
    }
    leaf fault-code {
      type notification-probable-cause-type;
      description
        "To describe the fault id of trap.";
    }
  }
  notification bad-bytes-error-rising {
    description
      "Port monitor bad bytes error rising.";
    leaf bad-bytes-error-statistics {
      type uint64;
      description
        "Port monitor bad bytes error statistics.";
    }
    leaf bad-bytes-error-threshold {
      type uint32;
      description
        "Port monitor bad bytes error threshold.";
    }
    leaf bad-bytes-error-interval {
      type uint32;
      description
        "Port monitor bad bytes error interval.";
    }
    leaf port-name {
      type string {
        length "1..32";
      }
      description
        "Port name of alarm monitor table.";
    }
  }
  notification bad-bytes-error-resume {
    description
      "Port monitor bad bytes error resume.";
    leaf bad-bytes-error-statistics {
      type uint64;
      description
        "Port monitor bad bytes error statistics.";
    }
    leaf bad-bytes-error-threshold {
      type uint32;
      description
        "Port monitor bad bytes error threshold.";
    }
    leaf bad-bytes-error-interval {
      type uint32;
      description
        "Port monitor bad bytes error interval.";
    }
    leaf port-name {
      type string {
        length "1..32";
      }
      description
        "Port name of alarm monitor table.";
    }
  }
  notification crc-error-rising {
    description
      "CRC error alarm.";
    leaf crc-error-statistics {
      type uint64;
      description
        "CRC error statistics value.";
    }
    leaf crc-error-threshold {
      type uint32;
      description
        "CRC error alarm threshold, default value is 3 and 0 is an invalid value.";
    }
    leaf crc-error-interval {
      type uint32;
      description
        "CRC error alarm interval time (unit is second), default value is 10s and 0 is an invalid value.";
    }
    leaf port-name {
      type string {
        length "1..32";
      }
      description
        "Port name of alarm monitor table.";
    }
  }
  notification crc-error-resume {
    description
      "CRC error alarm resume.";
    leaf crc-error-statistics {
      type uint64;
      description
        "CRC error statistics value.";
    }
    leaf crc-error-threshold {
      type uint32;
      description
        "CRC error alarm threshold, default value is 3 and 0 is an invalid value.";
    }
    leaf crc-error-interval {
      type uint32;
      description
        "CRC error alarm interval time (unit is second), default value is 10s and 0 is an invalid value.";
    }
    leaf port-name {
      type string {
        length "1..32";
      }
      description
        "Port name of alarm monitor table.";
    }
  }
  notification pause-frame-rising {
    description
      "Pause frame alarm.";
    leaf pause-frame-statistics {
      type uint64;
      description
        "Pause frame statistics value.";
    }
    leaf pause-frame-threshold {
      type uint32;
      description
        "Pause frame alarm threshold,and 0 is an invalid value.";
    }
    leaf pause-frame-interval {
      type uint32;
      description
        "Pause frame alarm interval time (unit is second),and 0 is an invalid value.";
    }
    leaf port-name {
      type string {
        length "1..32";
      }
      description
        "Port name of alarm monitor table.";
    }
  }
  notification pause-frame-resume {
    description
      "Pause frame alarm resume.";
    leaf pause-frame-statistics {
      type uint64;
      description
        "Pause frame statistics value.";
    }
    leaf pause-frame-threshold {
      type uint32;
      description
        "Pause frame alarm threshold,and 0 is an invalid value.";
    }
    leaf pause-frame-interval {
      type uint32;
      description
        "Pause frame alarm interval time (unit is second),and 0 is an invalid value.";
    }
    leaf port-name {
      type string {
        length "1..32";
      }
      description
        "Port name of alarm monitor table.";
    }
  }
  notification post-fec-error-rising {
    description
      "The post fec error crooected alarm appears.";
    leaf post-fec-error-statistics {
      type uint64;
      description
        "Indicates the post-FEC bit error statistics.";
    }
    leaf port-name {
      type string {
        length "1..32";
      }
      description
        "Port name of alarm monitor table.";
    }
  }
  notification post-fec-error-resume {
    description
      "The post fec error crooected alarm disappears.";
    leaf post-fec-error-statistics {
      type uint64;
      description
        "Indicates the post-FEC bit error statistics.";
    }
    leaf port-name {
      type string {
        length "1..32";
      }
      description
        "Port name of alarm monitor table.";
    }
  }
  notification sdh-b2-error-rising {
    description
      "Sdh B2 error alarm.";
    leaf sdh-b2-error-statistics {
      type uint64;
      description
        "Sdh B2 error statistics value.";
    }
    leaf sdh-b2-error-threshold {
      type uint32;
      description
        "Sdh error B2 alarm threshold,default value is 3.";
    }
    leaf sdh-b2-error-interval {
      type uint32;
      description
        "Sdh B2 error alarm interval time (unit is second),default value is 10s.";
    }
    leaf port-name {
      type string {
        length "1..32";
      }
      description
        "Port name of alarm monitor table.";
    }
  }
  notification sdh-b2-error-resume {
    description
      "Sdh B2 error alarm resume.";
    leaf sdh-b2-error-statistics {
      type uint64;
      description
        "Sdh B2 error statistics value.";
    }
    leaf sdh-b2-error-threshold {
      type uint32;
      description
        "Sdh error B2 alarm threshold,default value is 3.";
    }
    leaf sdh-b2-error-interval {
      type uint32;
      description
        "Sdh B2 error alarm interval time (unit is second),default value is 10s.";
    }
    leaf port-name {
      type string {
        length "1..32";
      }
      description
        "Port name of alarm monitor table.";
    }
  }
  notification sdh-error-rising {
    description
      "Sdh error alarm only for B3.";
    leaf sdh-error-statistics {
      type uint64;
      description
        "Sdh error statistics value only for B3.";
    }
    leaf sdh-error-threshold {
      type uint32;
      description
        "Sdh error alarm threshold,only for B3,default value is 3 and 0 is an invalid value.";
    }
    leaf sdh-error-interval {
      type uint32;
      description
        "Sdh error alarm interval time (unit is second), only for B3,default value is 10s and 0 is an invalid value.";
    }
    leaf port-name {
      type string {
        length "1..32";
      }
      description
        "Port name of alarm monitor table.";
    }
  }
  notification sdh-error-resume {
    description
      "Sdh error alarm resume only for B3.";
    leaf sdh-error-statistics {
      type uint64;
      description
        "Sdh error statistics value only for B3.";
    }
    leaf sdh-error-threshold {
      type uint32;
      description
        "Sdh error alarm threshold,only for B3, default value is 3 and 0 is an invalid value.";
    }
    leaf sdh-error-interval {
      type uint32;
      description
        "Sdh error alarm interval time (unit is second),only for B3, default value is 10s and 0 is an invalid value.";
    }
    leaf port-name {
      type string {
        length "1..32";
      }
      description
        "Port name of alarm monitor table.";
    }
  }
  notification symbol-error-interval {
    description
      "Symbol error alarm.";
    leaf symbol-error-statistics {
      type uint64;
      description
        "Symbol error statistics value.";
    }
    leaf symbol-error-threshold {
      type uint32;
      description
        "Symbol error alarm threshold,default value is 3.";
    }
    leaf symbol-error-interval {
      type uint32;
      description
        "Symbol error alarm interval time (unit is second), default value is 10s.";
    }
    leaf port-name {
      type string {
        length "1..32";
      }
      description
        "Port name of alarm monitor table.";
    }
  }
  notification symbol-error-interval-resume {
    description
      "CRC error alarm resume.";
    leaf symbol-error-statistics {
      type uint64;
      description
        "Symbol error statistics value.";
    }
    leaf symbol-error-threshold {
      type uint32;
      description
        "Symbol error alarm threshold,default value is 3.";
    }
    leaf symbol-error-interval {
      type uint32;
      description
        "Symbol error alarm interval time (unit is second), default value is 10s.";
    }
    leaf port-name {
      type string {
        length "1..32";
      }
      description
        "Port name of alarm monitor table.";
    }
  }
  notification tx-pause-frame-exceed {
    description
      "The threshold exceed alert of TX PAUSE appears.";
    leaf tx-pause-frame-statistics {
      type uint64;
      description
        "TX pause frame statistics value.";
    }
    leaf tx-pause-frame-high-threshold {
      type uint32;
      description
        "TX pause frame high threshold, and 0 is an invalid value.";
    }
    leaf tx-pause-frame-low-threshold {
      type uint32;
      description
        "TX pause frame low threshold, and 0 is an invalid value.";
    }
    leaf tx-pause-frame-interval {
      type uint32;
      description
        "TX pause frame alarm interval time (unit is second), and 0 is an invalid value.";
    }
    leaf port-name {
      type string {
        length "1..32";
      }
      description
        "Port name of alarm monitor table.";
    }
  }
  notification tx-pause-frame-exceed-resume {
    description
      "The threshold exceed alert of TX PAUSE disappears.";
    leaf tx-pause-frame-statistics {
      type uint64;
      description
        "TX pause frame statistics value.";
    }
    leaf tx-pause-frame-high-threshold {
      type uint32;
      description
        "TX pause frame high threshold, and 0 is an invalid value.";
    }
    leaf tx-pause-frame-low-threshold {
      type uint32;
      description
        "TX pause frame low threshold, and 0 is an invalid value.";
    }
    leaf tx-pause-frame-interval {
      type uint32;
      description
        "TX pause frame alarm interval time (unit is second), and 0 is an invalid value.";
    }
    leaf port-name {
      type string {
        length "1..32";
      }
      description
        "Port name of alarm monitor table.";
    }
  }
  notification input-error-exceed {
    description
      "This object indicates that an alarm is generated when the number of input errors on an interface exceeds the upper threshold.";
    leaf card-id {
      type uint32;
      description
        "Indicates the card ID.";
    }
    leaf port-name {
      type string {
        length "1..32";
      }
      description
        "Indicates the physical port name.";
    }
    leaf port-id {
      type uint32;
      description
        "Indicates the port ID.";
    }
    leaf slot-id {
      type uint32;
      description
        "Indicates the slot ID.";
    }
  }
  notification input-error-exceed-resume {
    description
      "This object indicates that a clear alarm is generated when the number of input errors on an interface falls below the upper threshold.";
    leaf card-id {
      type uint32;
      description
        "Indicates the card ID.";
    }
    leaf port-name {
      type string {
        length "1..32";
      }
      description
        "Indicates the physical port name.";
    }
    leaf port-id {
      type uint32;
      description
        "Indicates the port ID.";
    }
    leaf slot-id {
      type uint32;
      description
        "Indicates the slot ID.";
    }
  }
  notification multi-section {
    description
      "This object indicates the indication signal alarm in the MS.";
    leaf card-id {
      type uint32;
      description
        "Indicates the card ID.";
    }
    leaf port-name {
      type string {
        length "1..32";
      }
      description
        "Indicates the physical port name.";
    }
    leaf port-id {
      type uint32;
      description
        "Indicates the port ID.";
    }
    leaf slot-id {
      type uint32;
      description
        "Indicates the slot ID.";
    }
  }
  notification multi-section-resume {
    description
      "This object indicates that the indication signal alarm in the MS is cleared.";
    leaf card-id {
      type uint32;
      description
        "Indicates the card ID.";
    }
    leaf port-name {
      type string {
        length "1..32";
      }
      description
        "Indicates the physical port name.";
    }
    leaf port-id {
      type uint32;
      description
        "Indicates the port ID.";
    }
    leaf slot-id {
      type uint32;
      description
        "Indicates the slot ID.";
    }
  }
  notification laser-auto-shut {
    description
      "This object indicates that an alarm is generated when the optical laser is shut down automatically.";
    leaf card-id {
      type uint32;
      description
        "Indicates the card ID.";
    }
    leaf port-name {
      type string {
        length "1..32";
      }
      description
        "Indicates the physical port name.";
    }
    leaf port-id {
      type uint32;
      description
        "Indicates the port ID.";
    }
    leaf slot-id {
      type uint32;
      description
        "Indicates the slot ID.";
    }
  }
  notification laser-auto-shut-resume {
    description
      "This object indicates that the alarm for the automatic shutdown of the optical laser is cleared.";
    leaf card-id {
      type uint32;
      description
        "Indicates the card ID.";
    }
    leaf port-name {
      type string {
        length "1..32";
      }
      description
        "Indicates the physical port name.";
    }
    leaf port-id {
      type uint32;
      description
        "Indicates the port ID.";
    }
    leaf slot-id {
      type uint32;
      description
        "Indicates the slot ID.";
    }
  }
  notification laser-no-fited {
    description
      "The laser not installed alarm occured.";
    leaf entity-physical-index {
      type uint32;
      description
        "The index of physical.";
    }
    leaf port-name {
      type string {
        length "1..32";
      }
      description
        "Entity physical name.";
    }
  }
  notification laser-no-fited-resume {
    description
      "The laser not installed alarm resumed.";
    leaf entity-physical-index {
      type uint32;
      description
        "The index of physical.";
    }
    leaf port-name {
      type string {
        length "1..32";
      }
      description
        "Entity physical name.";
    }
  }
  notification laser-shut {
    description
      "This object indicates that an alarm is generated when the optical laser on a board is shut down.";
    leaf card-id {
      type uint32;
      description
        "Indicates the card ID.";
    }
    leaf port-name {
      type string {
        length "1..32";
      }
      description
        "Indicates the physical port name.";
    }
    leaf port-id {
      type uint32;
      description
        "Indicates the port ID.";
    }
    leaf slot-id {
      type uint32;
      description
        "Indicates the slot ID.";
    }
  }
  notification laser-shut-resume {
    description
      "This object indicates that a clear alarm is generated when the optical laser on a board is opened.";
    leaf card-id {
      type uint32;
      description
        "Indicates the card ID.";
    }
    leaf port-name {
      type string {
        length "1..32";
      }
      description
        "Indicates the physical port name.";
    }
    leaf port-id {
      type uint32;
      description
        "Indicates the port ID.";
    }
    leaf slot-id {
      type uint32;
      description
        "Indicates the slot ID.";
    }
  }
  notification license-resource-lack {
    description
      "Interfaces of this type in use exceeded the maximum number.";
    leaf license-type {
      type string {
        length "1..32";
      }
      description
        "Indicates the type of interface function-controlled license.";
    }
    leaf max-port-num {
      type uint32;
      description
        "Indicates the maximum number of available interfaces.";
    }
    leaf used-port-num {
      type uint32;
      description
        "Indicates the Number of interfaces in use.";
    }
  }
  notification license-resource-lack-resume {
    description
      "The maximum number-exceed alarm was cleared.";
    leaf license-type {
      type string {
        length "1..32";
      }
      description
        "Indicates the type of interface function-controlled license.";
    }
    leaf max-port-num {
      type uint32;
      description
        "Indicates the maximum number of available interfaces.";
    }
    leaf used-port-num {
      type uint32;
      description
        "Indicates the number of interfaces in use.";
    }
  }
  notification local-fault {
    description
      "This object indicates that an alarm is generated when the receive link from the remote device to the local device fails.";
    leaf physical-port-index {
      type uint32;
      description
        "Indicates the physical port index.";
    }
    leaf port-name {
      type string {
        length "1..32";
      }
      description
        "Indicates the physical port name.";
    }
  }
  notification local-fault-resume {
    description
      "This object indicates that a clear alarm is generated when the receive link from the remote device to the local device recovers.";
    leaf physical-port-index {
      type uint32;
      description
        "Indicates the physical port index.";
    }
    leaf port-name {
      type string {
        length "1..32";
      }
      description
        "Indicates the physical port name.";
    }
  }
  notification multi-loss-lp {
    description
      "This object indicates the loss of multiframe (LOM) on the higher order path (HP).";
    leaf card-id {
      type uint32;
      description
        "Indicates the card ID.";
    }
    leaf hp-id {
      type uint32;
      description
        "Indicates the higher order path ID.";
    }
    leaf port-name {
      type string {
        length "1..32";
      }
      description
        "Indicates the physical port name.";
    }
    leaf port-id {
      type uint32;
      description
        "Indicates the port ID.";
    }
    leaf slot-id {
      type uint32;
      description
        "Indicates the slot ID.";
    }
  }
  notification multi-loss-lp-resume {
    description
      "This object indicates that the LOM on the higher order path (HP) is resolved.";
    leaf card-id {
      type uint32;
      description
        "Indicates the card ID.";
    }
    leaf hp-id {
      type uint32;
      description
        "Indicates the higher order path ID.";
    }
    leaf port-name {
      type string {
        length "1..32";
      }
      description
        "Indicates the physical port name.";
    }
    leaf port-id {
      type uint32;
      description
        "Indicates the port ID.";
    }
    leaf slot-id {
      type uint32;
      description
        "Indicates the slot ID.";
    }
  }
  notification port-loopback {
    description
      "This object indicates that an alarm is generated due to an interface loopback.";
    leaf physical-port-index {
      type uint32;
      description
        "Indicates the physical port index.";
    }
    leaf port-name {
      type string {
        length "1..32";
      }
      description
        "Indicates the physical port name.";
    }
    leaf loop-type {
      type loop-type;
      description
        "Type of the notification loop. The value can be one -of the following: - 0: stop-loopback - 1: local - 2: remote.";
    }
  }
  notification port-loopback-resume {
    description
      "This object indicates that the alarm for the interface loopback is cleared.";
    leaf physical-port-index {
      type uint32;
      description
        "Indicates the physical port index.";
    }
    leaf port-name {
      type string {
        length "1..32";
      }
      description
        "Indicates the physical port name.";
    }
    leaf loop-type {
      type loop-type;
      description
        "Type of the notification loop. The value can be one -of the following: - 0: stop-loopback - 1: local - 2: remote.";
    }
  }
  notification signal-loss {
    description
      "This object indicates that an alarm is generated due to signal loss at the receive end.";
    leaf card-id {
      type uint32;
      description
        "Indicates the card ID.";
    }
    leaf port-name {
      type string {
        length "1..32";
      }
      description
        "Indicates the physical port name.";
    }
    leaf port-id {
      type uint32;
      description
        "Indicates the port ID.";
    }
    leaf slot-id {
      type uint32;
      description
        "Indicates the slot ID.";
    }
    leaf physical-port-alarm-name {
      type string {
        length "1..32";
      }
      description
        "Indicates the physical port alarm name.";
    }
  }
  notification signal-loss-resume {
    description
      "This object indicates that the alarm for the interface loopback is cleared.";
    leaf card-id {
      type uint32;
      description
        "Indicates the card ID.";
    }
    leaf port-name {
      type string {
        length "1..32";
      }
      description
        "Indicates the physical port name.";
    }
    leaf port-id {
      type uint32;
      description
        "Indicates the port ID.";
    }
    leaf slot-id {
      type uint32;
      description
        "Indicates the slot ID.";
    }
    leaf physical-port-alarm-name {
      type string {
        length "1..32";
      }
      description
        "Indicates the physical port alarm name.";
    }
  }
  notification remote-defect-ms {
    description
      "This object indicates that a line remote defect indicator (LRDI) alarm is generated in the multiplex section (MS) at the remote end.";
    leaf card-id {
      type uint32;
      description
        "Indicates the card ID.";
    }
    leaf port-name {
      type string {
        length "1..32";
      }
      description
        "Indicates the physical port name.";
    }
    leaf port-id {
      type uint32;
      description
        "Indicates the port ID.";
    }
    leaf slot-id {
      type uint32;
      description
        "Indicates the slot ID.";
    }
  }
  notification remote-defect-ms-resume {
    description
      "This object indicates that the LRDI alarm generated in the multiplex section (MS) at the remote end is cleared.";
    leaf card-id {
      type uint32;
      description
        "Indicates the card ID.";
    }
    leaf port-name {
      type string {
        length "1..32";
      }
      description
        "Indicates the physical port name.";
    }
    leaf port-id {
      type uint32;
      description
        "Indicates the port ID.";
    }
    leaf slot-id {
      type uint32;
      description
        "Indicates the slot ID.";
    }
  }
  notification negotiation-failed {
    description
      "Auto-negotiation failure alarm. Possible causes, including the local auto-negotiation configuration with the peer inconsistencies; 
              the local ability is not compatible with the peer; 
              the physical connection of the two sides is unstable. 
              When the alarm occurs, the port can't be up.";
    leaf physical-port-index {
      type uint32;
      description
        "Indicates the physical port index.";
    }
    leaf port-name {
      type string {
        length "1..32";
      }
      description
        "Indicates the physical port name.";
    }
  }
  notification negotiation-failed-resume {
    description
      "Auto-negotiation failure alarm resume.";
    leaf physical-port-index {
      type uint32;
      description
        "Indicates the physical port index.";
    }
    leaf port-name {
      type string {
        length "1..32";
      }
      description
        "Indicates the physical port name.";
    }
  }
  notification odu-indication-signal {
    description
      "This object indicates the ODU indication signal alarm.";
    leaf card-id {
      type uint32;
      description
        "Indicates the card ID.";
    }
    leaf port-name {
      type string {
        length "1..32";
      }
      description
        "Indicates the physical port name.";
    }
    leaf port-id {
      type uint32;
      description
        "Indicates the port ID.";
    }
    leaf slot-id {
      type uint32;
      description
        "Indicates the slot ID.";
    }
  }
  notification odu-indication-signal-resume {
    description
      "This object indicates that the ODU indication signal alarm is cleared.";
    leaf card-id {
      type uint32;
      description
        "Indicates the card ID.";
    }
    leaf port-name {
      type string {
        length "1..32";
      }
      description
        "Indicates the physical port name.";
    }
    leaf port-id {
      type uint32;
      description
        "Indicates the port ID.";
    }
    leaf slot-id {
      type uint32;
      description
        "Indicates the slot ID.";
    }
  }
  notification odu-locked-signal {
    description
      "This object indicates the ODU lock defect alarm.";
    leaf card-id {
      type uint32;
      description
        "Indicates the card ID.";
    }
    leaf port-name {
      type string {
        length "1..32";
      }
      description
        "Indicates the physical port name.";
    }
    leaf port-id {
      type uint32;
      description
        "Indicates the port ID.";
    }
    leaf slot-id {
      type uint32;
      description
        "Indicates the slot ID.";
    }
  }
  notification odu-locked-signal-resume {
    description
      "This object indicates that the ODU lock defect alarm is cleared.";
    leaf card-id {
      type uint32;
      description
        "Indicates the card ID.";
    }
    leaf port-name {
      type string {
        length "1..32";
      }
      description
        "Indicates the physical port name.";
    }
    leaf port-id {
      type uint32;
      description
        "Indicates the port ID.";
    }
    leaf slot-id {
      type uint32;
      description
        "Indicates the slot ID.";
    }
  }
  notification odu-open-connection {
    description
      "This object indicates that the indication defect alarm for the ODU open connection.";
    leaf card-id {
      type uint32;
      description
        "Indicates the card ID.";
    }
    leaf port-name {
      type string {
        length "1..32";
      }
      description
        "Indicates the physical port name.";
    }
    leaf port-id {
      type uint32;
      description
        "Indicates the port ID.";
    }
    leaf slot-id {
      type uint32;
      description
        "Indicates the slot ID.";
    }
  }
  notification odu-open-connection-resume {
    description
      "This object indicates that the indication defect alarm for the ODU open connection is cleared.";
    leaf card-id {
      type uint32;
      description
        "Indicates the card ID.";
    }
    leaf port-name {
      type string {
        length "1..32";
      }
      description
        "Indicates the physical port name.";
    }
    leaf port-id {
      type uint32;
      description
        "Indicates the port ID.";
    }
    leaf slot-id {
      type uint32;
      description
        "Indicates the slot ID.";
    }
  }
  notification odu-signal-degrade {
    description
      "This object indicates that an alarm is generated for the ODU signal degrade.";
    leaf card-id {
      type uint32;
      description
        "Indicates the card ID.";
    }
    leaf port-name {
      type string {
        length "1..32";
      }
      description
        "Indicates the physical port name.";
    }
    leaf port-id {
      type uint32;
      description
        "Indicates the port ID.";
    }
    leaf slot-id {
      type uint32;
      description
        "Indicates the slot ID.";
    }
  }
  notification odu-signal-degrade-resume {
    description
      "This object indicates that the alarm for the ODU signal degrade is cleared.";
    leaf card-id {
      type uint32;
      description
        "Indicates the card ID.";
    }
    leaf port-name {
      type string {
        length "1..32";
      }
      description
        "Indicates the physical port name.";
    }
    leaf port-id {
      type uint32;
      description
        "Indicates the port ID.";
    }
    leaf slot-id {
      type uint32;
      description
        "Indicates the slot ID.";
    }
  }
  notification out-of-frame {
    description
      "This object indicates that an out of frame (OOF) alarm is generated at the receive end.";
    leaf card-id {
      type uint32;
      description
        "Indicates the card ID.";
    }
    leaf port-name {
      type string {
        length "1..32";
      }
      description
        "Indicates the physical port name.";
    }
    leaf port-id {
      type uint32;
      description
        "Indicates the port ID.";
    }
    leaf slot-id {
      type uint32;
      description
        "Indicates the slot ID.";
    }
  }
  notification out-of-frame-resume {
    description
      "This object indicates that the OOF alarm generated at the receive end is cleared.";
    leaf card-id {
      type uint32;
      description
        "Indicates the card ID.";
    }
    leaf port-name {
      type string {
        length "1..32";
      }
      description
        "Indicates the physical port name.";
    }
    leaf port-id {
      type uint32;
      description
        "Indicates the port ID.";
    }
    leaf slot-id {
      type uint32;
      description
        "Indicates the slot ID.";
    }
  }
  notification optical-not-match {
    description
      "After the optical module was inserted, its configuration was not supported. The partial function of optical module failed.";
    leaf entity-physical-index {
      type uint32;
      description
        "The index of physical.";
    }
    leaf port-name {
      type string {
        length "1..32";
      }
      description
        "Entity physical name.";
    }
    leaf fault-code {
      type notification-probable-cause-type;
      description
        "To describe the fault id of trap.";
    }
    leaf reason {
      type string {
        length "1..32";
      }
      description
        "Description of trap reason.";
    }
  }
  notification optical-not-match-resume {
    description
      "After the optical module was inserted, its configuration was not supported. The partial function of optical module failed.";
    leaf entity-physical-index {
      type uint32;
      description
        "The index of physical.";
    }
    leaf port-name {
      type string {
        length "1..32";
      }
      description
        "Entity physical name.";
    }
    leaf fault-code {
      type notification-probable-cause-type;
      description
        "To describe the fault id of trap.";
    }
    leaf reason {
      type string {
        length "1..32";
      }
      description
        "Description of trap reason.";
    }
  }
  notification optical-fail {
    description
      "Optical Module become failure for some reason.";
    leaf entity-physical-index {
      type uint32;
      description
        "The index of physical.";
    }
    leaf port-name {
      type string {
        length "1..32";
      }
      description
        "Entity physical name.";
    }
    leaf fault-code {
      type notification-probable-cause-type;
      description
        "To describe the fault id of trap.";
    }
    leaf reason {
      type string {
        length "1..32";
      }
      description
        "Description of trap reason.";
    }
  }
  notification optical-fail-resume {
    description
      "Optical Module resume from failure.";
    leaf entity-physical-index {
      type uint32;
      description
        "The index of physical.";
    }
    leaf port-name {
      type string {
        length "1..32";
      }
      description
        "Entity physical name.";
    }
    leaf fault-code {
      type notification-probable-cause-type;
      description
        "To describe the fault id of trap.";
    }
    leaf reason {
      type string {
        length "1..32";
      }
      description
        "Description of trap reason.";
    }
  }
  notification optical-not-authorized {
    description
      "This object indicates that an alarm is generated when the inserted optical module is one not authenticated by Huawei.";
    leaf physical-port-index {
      type uint32;
      description
        "This object indicates the index of a physical port.";
    }
    leaf port-name {
      type string {
        length "1..32";
      }
      description
        "This object indicates the name of a physical port.";
    }
  }
  notification optical-not-authorized-resume {
    description
      "This object indicates that an alarm is generated when the inserted optical module is one not authenticated by Huawei.";
    leaf physical-port-index {
      type uint32;
      description
        "This object indicates the index of a physical port.";
    }
    leaf port-name {
      type string {
        length "1..32";
      }
      description
        "This object indicates the name of a physical port.";
    }
  }
  notification otu-indication-signal {
    description
      "This object indicates the OTU indication signal alarm.";
    leaf card-id {
      type uint32;
      description
        "Indicates the card ID.";
    }
    leaf port-name {
      type string {
        length "1..32";
      }
      description
        "Indicates the physical port name.";
    }
    leaf port-id {
      type uint32;
      description
        "Indicates the port ID.";
    }
    leaf slot-id {
      type uint32;
      description
        "Indicates the slot ID.";
    }
  }
  notification otu-indication-signal-resume {
    description
      "This object indicates that the OTU indication signal alarm is cleared.";
    leaf card-id {
      type uint32;
      description
        "Indicates the card ID.";
    }
    leaf port-name {
      type string {
        length "1..32";
      }
      description
        "Indicates the physical port name.";
    }
    leaf port-id {
      type uint32;
      description
        "Indicates the port ID.";
    }
    leaf slot-id {
      type uint32;
      description
        "Indicates the slot ID.";
    }
  }
  notification otu-loss-of-multiframe {
    description
      "This object indicates the OTU indication signal alarm.";
    leaf card-id {
      type uint32;
      description
        "Indicates the card ID.";
    }
    leaf port-name {
      type string {
        length "1..32";
      }
      description
        "Indicates the physical port name.";
    }
    leaf port-id {
      type uint32;
      description
        "Indicates the port ID.";
    }
    leaf slot-id {
      type uint32;
      description
        "Indicates the slot ID.";
    }
  }
  notification otu-loss-of-multiframe-resume {
    description
      "This object indicates that the OTU indication signal alarm is cleared.";
    leaf card-id {
      type uint32;
      description
        "Indicates the card ID.";
    }
    leaf port-name {
      type string {
        length "1..32";
      }
      description
        "Indicates the physical port name.";
    }
    leaf port-id {
      type uint32;
      description
        "Indicates the port ID.";
    }
    leaf slot-id {
      type uint32;
      description
        "Indicates the slot ID.";
    }
  }
  notification otu-signal-degrade {
    description
      "This object indicates that an alarm is generated for the OTU signal degrade.";
    leaf card-id {
      type uint32;
      description
        "Indicates the card ID.";
    }
    leaf port-name {
      type string {
        length "1..32";
      }
      description
        "Indicates the physical port name.";
    }
    leaf port-id {
      type uint32;
      description
        "Indicates the port ID.";
    }
    leaf slot-id {
      type uint32;
      description
        "Indicates the slot ID.";
    }
  }
  notification otu-signal-degrade-resume {
    description
      "This object indicates that the alarm for the OTU signal degrade is cleared.";
    leaf card-id {
      type uint32;
      description
        "Indicates the card ID.";
    }
    leaf port-name {
      type string {
        length "1..32";
      }
      description
        "Indicates the physical port name.";
    }
    leaf port-id {
      type uint32;
      description
        "Indicates the port ID.";
    }
    leaf slot-id {
      type uint32;
      description
        "Indicates the slot ID.";
    }
  }
  notification otu-signal-fail {
    description
      "This object indicates that an alarm is generated for the OTU signal failure.";
    leaf card-id {
      type uint32;
      description
        "Indicates the card ID.";
    }
    leaf port-name {
      type string {
        length "1..32";
      }
      description
        "Indicates the physical port name.";
    }
    leaf port-id {
      type uint32;
      description
        "Indicates the port ID.";
    }
    leaf slot-id {
      type uint32;
      description
        "Indicates the slot ID.";
    }
  }
  notification otu-signal-fail-resume {
    description
      "This object indicates that the alarm for the OTU signal degrade is cleared.";
    leaf card-id {
      type uint32;
      description
        "Indicates the card ID.";
    }
    leaf port-name {
      type string {
        length "1..32";
      }
      description
        "Indicates the physical port name.";
    }
    leaf port-id {
      type uint32;
      description
        "Indicates the port ID.";
    }
    leaf slot-id {
      type uint32;
      description
        "Indicates the slot ID.";
    }
  }
  notification output-error-exceed {
    description
      "This object indicates that an alarm is generated when the number of output errors on an interface exceeds the upper threshold.";
    leaf card-id {
      type uint32;
      description
        "Indicates the card ID.";
    }
    leaf port-name {
      type string {
        length "1..32";
      }
      description
        "Indicates the physical port name.";
    }
    leaf port-id {
      type uint32;
      description
        "Indicates the port ID.";
    }
    leaf slot-id {
      type uint32;
      description
        "Indicates the slot ID.";
    }
  }
  notification output-error-exceed-resume {
    description
      "This object indicates that a clear alarm is generated when the number of output errors on an interface falls below the upper threshold.";
    leaf card-id {
      type uint32;
      description
        "Indicates the card ID.";
    }
    leaf port-name {
      type string {
        length "1..32";
      }
      description
        "Indicates the physical port name.";
    }
    leaf port-id {
      type uint32;
      description
        "Indicates the port ID.";
    }
    leaf slot-id {
      type uint32;
      description
        "Indicates the slot ID.";
    }
  }
  notification signal-lp {
    description
      "This object indicates that a low path alarm indication signal is detected.";
    leaf card-id {
      type uint32;
      description
        "Indicates the card ID.";
    }
    leaf port-name {
      type string {
        length "1..32";
      }
      description
        "Indicates the physical port name.";
    }
    leaf port-id {
      type uint32;
      description
        "Indicates the port ID.";
    }
    leaf slot-id {
      type uint32;
      description
        "Indicates the slot ID.";
    }
    leaf hp-id {
      type uint32;
      description
        "Indicates the higher order path ID.";
    }
  }
  notification signal-lp-resume {
    description
      "This object indicates that a low path alarm indication signal is detected.";
    leaf card-id {
      type uint32;
      description
        "Indicates the card ID.";
    }
    leaf port-name {
      type string {
        length "1..32";
      }
      description
        "Indicates the physical port name.";
    }
    leaf port-id {
      type uint32;
      description
        "Indicates the port ID.";
    }
    leaf slot-id {
      type uint32;
      description
        "Indicates the slot ID.";
    }
    leaf hp-id {
      type uint32;
      description
        "Indicates the higher order path ID.";
    }
  }
  notification bip8-sd-error {
    description
      "This object indicates the output error alarm.";
    leaf physical-port-index {
      type uint32;
      description
        "This object indicates the index of a physical port.";
    }
    leaf port-name {
      type string {
        length "1..64";
      }
      description
        "This object indicates the name of a physical port.";
    }
    leaf physical-port-bip8-sd-error-threshold {
      type uint32;
      description
        "This object indicates the BIP8 SD alarm threshold. The default value is 6.";
    }
  }
  notification bip8-sd-error-resume {
    description
      "This object indicates that the Output error alarm is cleared.";
    leaf physical-port-index {
      type uint32;
      description
        "This object indicates the index of a physical port.";
    }
    leaf port-name {
      type string {
        length "1..64";
      }
      description
        "This object indicates the name of a physical port.";
    }
    leaf physical-port-bip8-sd-error-threshold {
      type uint32;
      description
        "This object indicates the BIP8 SD alarm threshold. The default value is 6.";
    }
  }
  notification crc-error-exceed {
    description
      "Port CRC error alarm.";
    leaf physical-port-index {
      type uint32;
      description
        "This object indicates the index of a physical port.";
    }
    leaf port-name {
      type string {
        length "1..64";
      }
      description
        "This object indicates the name of a physical port.";
    }
    leaf physical-port-crc-error-statistics {
      type uint64;
      description
        "This object indicates the CRC error statistics.";
    }
    leaf physical-port-crc-error-high-threshold {
      type uint32;
      description
        "This object indicates the upper threshold for the number of CRC errors. The default value is 1000 pps.";
    }
    leaf physical-port-crc-error-low-threshold {
      type uint32;
      description
        "This object indicates the lower threshold for the number of CRC errors. The default value is 100 pps.";
    }
    leaf physical-port-crc-error-interval {
      type uint32;
      description
        "This object indicates the time threshold for the CRC error alarm. The default value is 10s.";
    }
  }
  notification crc-error-exceed-resume {
    description
      "Port CRC error alarm resume.";
    leaf physical-port-index {
      type uint32;
      description
        "This object indicates the index of a physical port.";
    }
    leaf port-name {
      type string {
        length "1..64";
      }
      description
        "This object indicates the name of a physical port.";
    }
    leaf physical-port-crc-error-statistics {
      type uint64;
      description
        "This object indicates the CRC error statistics.";
    }
    leaf physical-port-crc-error-high-threshold {
      type uint32;
      description
        "This object indicates the upper threshold for the number of CRC errors. The default value is 1000 pps.";
    }
    leaf physical-port-crc-error-low-threshold {
      type uint32;
      description
        "This object indicates the lower threshold for the number of CRC errors. The default value is 100 pps.";
    }
    leaf physical-port-crc-error-interval {
      type uint32;
      description
        "This object indicates the time threshold for the CRC error alarm. The default value is 10s.";
    }
  }
  notification crc-fcs-exceed {
    description
      "Port MAC FCS EXC alarm.";
    leaf physical-port-index {
      type uint32;
      description
        "This object indicates the index of a physical port.";
    }
    leaf port-name {
      type string {
        length "1..64";
      }
      description
        "This object indicates the name of a physical port.";
    }
    leaf current-crc-packet-error-ratio {
      type string {
        length "1..32";
      }
      description
        "This object indicates that the thresholds for CRC error packet ratio alarms on a physical port are sent to the NMS in the character string format.";
    }
    leaf physical-port-crc-exc-alarm-threshold {
      type string {
        length "1..32";
      }
      description
        "The alarm threshold of MAC_FCS_EXC.";
    }
    leaf physical-port-crc-exc-resume-threshold {
      type string {
        length "1..32";
      }
      description
        "The resume threshold of MAC_FCS_EXC.";
    }
  }
  notification crc-fcs-exceed-resume {
    description
      "Port MAC_FCS_EXC alarm resume.";
    leaf physical-port-index {
      type uint32;
      description
        "This object indicates the index of a physical port.";
    }
    leaf port-name {
      type string {
        length "1..64";
      }
      description
        "This object indicates the name of a physical port.";
    }
    leaf current-crc-packet-error-ratio {
      type string {
        length "1..32";
      }
      description
        "This object indicates that the thresholds for CRC error packet ratio alarms on a physical port are sent to the NMS in the character string format.";
    }
    leaf physical-port-crc-exc-alarm-threshold {
      type string {
        length "1..32";
      }
      description
        "The alarm threshold of MAC_FCS_EXC.";
    }
    leaf physical-port-crc-exc-resume-threshold {
      type string {
        length "1..32";
      }
      description
        "The resume threshold of MAC_FCS_EXC.";
    }
  }
  notification crc-packet-error-ratio {
    description
      "This object indicates that an alarm is generated when the number of CRC errors on a physical port exceeds the upper threshold. The host sends a trap message to the NMS.";
    leaf physical-port-index {
      type uint32;
      description
        "This object indicates the index of a physical port.";
    }
    leaf port-name {
      type string {
        length "1..64";
      }
      description
        "This object indicates the name of a physical port.";
    }
    leaf current-crc-packet-error-ratio {
      type string {
        length "1..32";
      }
      description
        "This object indicates that the thresholds for CRC error packet ratio alarms on a physical port are sent to the NMS in the character string format.";
    }
    leaf alarm-threshold {
      type string {
        length "1..32";
      }
      description
        "This object indicates that the generation threshold for the CRC error packet ratio alarm on a physical port is sent to the NMS in the character string format.";
    }
    leaf resume-threshold {
      type string {
        length "1..32";
      }
      description
        "This object indicates that the clearing threshold for the CRC error packet ratio clear alarm on a physical port is sent to the NMS in the character string format.";
    }
  }
  notification crc-packet-error-ratio-resume {
    description
      "This object indicates that a clear alarm is generated when the number of CRC errors on a physical port falls below the upper threshold. The host sends a trap message to the NMS.";
    leaf physical-port-index {
      type uint32;
      description
        "This object indicates the index of a physical port.";
    }
    leaf port-name {
      type string {
        length "1..64";
      }
      description
        "This object indicates the name of a physical port.";
    }
    leaf current-crc-packet-error-ratio {
      type string {
        length "1..32";
      }
      description
        "This object indicates that the thresholds for CRC error packet ratio alarms on a physical port are sent to the NMS in the character string format.";
    }
    leaf alarm-threshold {
      type string {
        length "1..32";
      }
      description
        "This object indicates that the generation threshold for the CRC error packet ratio alarm on a physical port is sent to the NMS in the character string format.";
    }
    leaf resume-threshold {
      type string {
        length "1..32";
      }
      description
        "This object indicates that the clearing threshold for the CRC error packet ratio clear alarm on a physical port is sent to the NMS in the character string format.";
    }
  }
  notification crc-error-warning {
    description
      "This object indicates that an alarm is generated when the number of CRC errors on a physical port exceeds the lower threshold. The host sends a trap message to the NMS.";
    leaf physical-port-index {
      type uint32;
      description
        "This object indicates the index of a physical port.";
    }
    leaf port-name {
      type string {
        length "1..64";
      }
      description
        "This object indicates the name of a physical port.";
    }
    leaf current-crc-packet-error-ratio {
      type string {
        length "1..32";
      }
      description
        "This object indicates that the thresholds for CRC error packet ratio alarms on a physical port are sent to the NMS in the character string format.";
    }
    leaf crc-per-warning-threshold {
      type string {
        length "1..32";
      }
      description
        "The warning threshold of CRC-PER (Packet Error Ratio).";
    }
    leaf physical-port-crc-per-warning-resume-threshold {
      type string {
        length "1..32";
      }
      description
        "The warning resume threshold of CRC-PER (Packet Error Ratio).";
    }
  }
  notification crc-error-warning-resume {
    description
      "This object indicates that a clear alarm is generated when the number of CRC errors on a physical port falls below the lower threshold. The host sends a trap message to the NMS.";
    leaf physical-port-index {
      type uint32;
      description
        "This object indicates the index of a physical port.";
    }
    leaf port-name {
      type string {
        length "1..64";
      }
      description
        "This object indicates the name of a physical port.";
    }
    leaf current-crc-packet-error-ratio {
      type string {
        length "1..32";
      }
      description
        "This object indicates that the thresholds for CRC error packet ratio alarms on a physical port are sent to the NMS in the character string format.";
    }
    leaf physical-port-crc-per-warning-threshold {
      type string {
        length "1..32";
      }
      description
        "The warning threshold of CRC-PER (Packet Error Ratio).";
    }
    leaf physical-port-crc-per-warning-resume-threshold {
      type string {
        length "1..32";
      }
      description
        "The warning resume threshold of CRC-PER (Packet Error Ratio).";
    }
  }
  notification crc-mac-fcs-sd {
    description
      "This object indicates that an alarm when port FCS signal degrade at the MAC layer.";
    leaf physical-port-index {
      type uint32;
      description
        "This object indicates the index of a physical port.";
    }
    leaf port-name {
      type string {
        length "1..64";
      }
      description
        "This object indicates the name of a physical port.";
    }
    leaf current-crc-packet-error-ratio {
      type string {
        length "1..32";
      }
      description
        "This object indicates that the thresholds for CRC error packet ratio alarms on a physical port are sent to the NMS in the character string format.";
    }
    leaf physical-port-crc-sd-alarm-threshold {
      type string {
        length "1..32";
      }
      description
        "The alarm threshold of MAC_FCS_SD.";
    }
    leaf physical-port-crc-sd-resume-threshold {
      type string {
        length "1..32";
      }
      description
        "The resume threshold of MAC_FCS_SD.";
    }
  }
  notification crc-mac-fcs-sd-resume {
    description
      "This object indicates that a clear alarm when port FCS signal degrade at the MAC layer.";
    leaf physical-port-index {
      type uint32;
      description
        "This object indicates the index of a physical port.";
    }
    leaf port-name {
      type string {
        length "1..64";
      }
      description
        "This object indicates the name of a physical port.";
    }
    leaf current-crc-packet-error-ratio {
      type string {
        length "1..32";
      }
      description
        "This object indicates that the thresholds for CRC error packet ratio alarms on a physical port are sent to the NMS in the character string format.";
    }
    leaf physical-port-crc-sd-alarm-threshold {
      type string {
        length "1..32";
      }
      description
        "The alarm threshold of MAC_FCS_SD.";
    }
    leaf physical-port-crc-sd-resume-threshold {
      type string {
        length "1..32";
      }
      description
        "The resume threshold of MAC_FCS_SD.";
    }
  }
  notification path-trace-mismatch {
    description
      "This object indicates that an alarm is generated when path trace identifiers between the local and remote ends mismatch.";
    leaf card-id {
      type uint32;
      description
        "Indicates the card ID.";
    }
    leaf port-name {
      type string {
        length "1..32";
      }
      description
        "Indicates the physical port name.";
    }
    leaf port-id {
      type uint32;
      description
        "Indicates the port ID.";
    }
    leaf slot-id {
      type uint32;
      description
        "Indicates the slot ID.";
    }
  }
  notification path-trace-mismatch-resume {
    description
      "This object indicates that a clear alarm is generated when path trace identifiers between the local and remote ends match.";
    leaf card-id {
      type uint32;
      description
        "Indicates the card ID.";
    }
    leaf port-name {
      type string {
        length "1..32";
      }
      description
        "Indicates the physical port name.";
    }
    leaf port-id {
      type uint32;
      description
        "Indicates the port ID.";
    }
    leaf slot-id {
      type uint32;
      description
        "Indicates the slot ID.";
    }
  }
  notification trans-mode-inconsistent {
    description
      "The transmission modes of the group of interfaces are inconsistent.";
    leaf card-id {
      type uint32;
      description
        "Indicates the card ID.";
    }
    leaf physical-port-groupid {
      type string {
        length "1..32";
      }
      description
        "Indicates the physical port group id.";
    }
    leaf port-trans-mode-reason {
      type string {
        length "1..32";
      }
      description
        "Indicates the physical port transmission mode different reason.";
    }
    leaf slot-id {
      type uint32;
      description
        "Indicates the slot ID.";
    }
  }
  notification trans-mode-inconsistent-resume {
    description
      "The transmission modes of the group of interfaces are consistent now.";
    leaf card-id {
      type uint32;
      description
        "Indicates the card ID.";
    }
    leaf physical-port-groupid {
      type string {
        length "1..32";
      }
      description
        "Indicates the physical port group id.";
    }
    leaf port-trans-mode-reason {
      type string {
        length "1..32";
      }
      description
        "Indicates the physical port transmission mode different reason.";
    }
    leaf slot-id {
      type uint32;
      description
        "Indicates the slot ID.";
    }
  }
  notification port-mode-change {
    description
      "This object indicates that the port rate type is changed.";
    leaf physical-port-index {
      type uint32;
      description
        "Indicates the physical port index.";
    }
    leaf port-name {
      type string {
        length "1..32";
      }
      description
        "Indicates the physical port name.";
    }
    leaf physical-port-mode {
      type uint32;
      description
        "The current state of port type in port.";
    }
  }
  notification port-physical-down {
    description
      "One of the port physical connect down.";
    leaf base-trap-severity {
      type uint32;
      description
        "To describe the level of trap.";
    }
    leaf base-trap-probable-cause {
      type uint32;
      description
        "To describe the probable cause of trap.";
    }
    leaf base-trap-event-type {
      type uint32;
      description
        "To describe the type of trap.";
    }
    leaf port-name {
      type string {
        length "1..32";
      }
      description
        "Entity physical name.";
    }
    leaf port-physical-down-reason {
      type string {
        length "1..32";
      }
      description
        "Port physical down reason.";
    }
  }
  notification port-physical-up {
    description
      "One of the port physical connect up.";
    leaf base-trap-severity {
      type uint32;
      description
        "To describe the level of trap.";
    }
    leaf base-trap-probable-cause {
      type uint32;
      description
        "To describe the probable cause of trap.";
    }
    leaf base-trap-event-type {
      type uint32;
      description
        "To describe the type of trap.";
    }
    leaf port-name {
      type string {
        length "1..32";
      }
      description
        "Entity physical name.";
    }
  }
  notification physical-rate-degrade {
    description
      "This object indicates that an alarm is generated when the negotiation rate on an electrical interface falls sharply.";
    leaf physical-port-index {
      type uint32;
      description
        "Indicates the physical port index.";
    }
  }
  notification physical-rate-degrade-resume {
    description
      "This object indicates that a clear alarm is generated when the negotiation rate on an electrical interface falls sharply.";
    leaf physical-port-index {
      type uint32;
      description
        "Indicates the physical port index.";
    }
  }
  notification traffic-fall-receive {
    description
      "Traffic fall alarm in the receive direction of an Ethernet interface.";
    leaf physical-port-index {
      type uint32;
      description
        "Indicates the physical port index.";
    }
  }
  notification traffic-fall-receive-resume {
    description
      "Traffic fall clear alarm in the receive direction of an Ethernet interface.";
    leaf physical-port-index {
      type uint32;
      description
        "Indicates the physical port index.";
    }
  }
  notification port-type-change {
    description
      "The mode of combo port is changed.";
    leaf physical-port-index {
      type uint32;
      description
        "Indicates the physical port index.";
    }
    leaf port-name {
      type string {
        length "1..32";
      }
      description
        "Indicates the physical port name.";
    }
    leaf physical-port-mode {
      type uint32;
      description
        "The current state of port type in port.";
    }
  }
  notification payload-mismatch-hp {
    description
      "This object indicates the higher order path (HP) signal identifier mismatch.";
    leaf card-id {
      type uint32;
      description
        "Indicates the card ID.";
    }
    leaf hp-id {
      type uint32;
      description
        "Indicates the higher order path ID.";
    }
    leaf port-name {
      type string {
        length "1..32";
      }
      description
        "Indicates the physical port name.";
    }
    leaf port-id {
      type uint32;
      description
        "Indicates the port ID.";
    }
    leaf slot-id {
      type uint32;
      description
        "Indicates the slot ID.";
    }
  }
  notification payload-mismatch-hp-resume {
    description
      "This object indicates that the higher order path (HP) signal identifier mismatch is rectified.";
    leaf card-id {
      type uint32;
      description
        "Indicates the card ID.";
    }
    leaf hp-id {
      type uint32;
      description
        "Indicates the higher order path ID.";
    }
    leaf port-name {
      type string {
        length "1..32";
      }
      description
        "Indicates the physical port name.";
    }
    leaf port-id {
      type uint32;
      description
        "Indicates the port ID.";
    }
    leaf slot-id {
      type uint32;
      description
        "Indicates the slot ID.";
    }
  }
  notification remote-defect-hp {
    description
      "This object indicates the higher order path (HP) Remote Default Indication (HPRDI) alarm.";
    leaf card-id {
      type uint32;
      description
        "Indicates the card ID.";
    }
    leaf hp-id {
      type uint32;
      description
        "Indicates the higher order path ID.";
    }
    leaf port-name {
      type string {
        length "1..32";
      }
      description
        "Indicates the physical port name.";
    }
    leaf port-id {
      type uint32;
      description
        "Indicates the port ID.";
    }
    leaf slot-id {
      type uint32;
      description
        "Indicates the slot ID.";
    }
  }
  notification remote-defect-hp-resume {
    description
      "This object indicates the higher order path (HP) Remote Default Indication (HPRDI) alarm is cleared.";
    leaf card-id {
      type uint32;
      description
        "Indicates the card ID.";
    }
    leaf hp-id {
      type uint32;
      description
        "Indicates the higher order path ID.";
    }
    leaf port-name {
      type string {
        length "1..32";
      }
      description
        "Indicates the physical port name.";
    }
    leaf port-id {
      type uint32;
      description
        "Indicates the port ID.";
    }
    leaf slot-id {
      type uint32;
      description
        "Indicates the slot ID.";
    }
  }
  notification pre-fec-tca {
    description
      "This object indicates that an alarm is generated for forward error correction (FEC) bit errors threshold-crossing.";
    leaf card-id {
      type uint32;
      description
        "Indicates the card ID.";
    }
    leaf port-name {
      type string {
        length "1..32";
      }
      description
        "Indicates the physical port name.";
    }
    leaf port-id {
      type uint32;
      description
        "Indicates the port ID.";
    }
    leaf slot-id {
      type uint32;
      description
        "Indicates the slot ID.";
    }
  }
  notification prefec-tca-resume {
    description
      "This object indicates that a clear is generated for forward error correction (FEC) bit errors threshold-crossing.";
    leaf card-id {
      type uint32;
      description
        "Indicates the card ID.";
    }
    leaf port-name {
      type string {
        length "1..32";
      }
      description
        "Indicates the physical port name.";
    }
    leaf port-id {
      type uint32;
      description
        "Indicates the port ID.";
    }
    leaf slot-id {
      type uint32;
      description
        "Indicates the slot ID.";
    }
  }
  notification trace-mismatch-hp {
    description
      "This object indicates that an alarm is generated when the higher order path (HP) trace identifier is unstable.";
    leaf card-id {
      type uint32;
      description
        "Indicates the card ID.";
    }
    leaf hp-id {
      type uint32;
      description
        "Indicates the higher order path ID.";
    }
    leaf port-name {
      type string {
        length "1..32";
      }
      description
        "Indicates the physical port name.";
    }
    leaf port-id {
      type uint32;
      description
        "Indicates the port ID.";
    }
    leaf slot-id {
      type uint32;
      description
        "Indicates the slot ID.";
    }
  }
  notification trace-mismatch-hp-resume {
    description
      "This object indicates that a clear alarm is generated when the higher order path (HP) trace identifier becomes stable.";
    leaf card-id {
      type uint32;
      description
        "Indicates the card ID.";
    }
    leaf hp-id {
      type uint32;
      description
        "Indicates the higher order path ID.";
    }
    leaf port-name {
      type string {
        length "1..32";
      }
      description
        "Indicates the physical port name.";
    }
    leaf port-id {
      type uint32;
      description
        "Indicates the port ID.";
    }
    leaf slot-id {
      type uint32;
      description
        "Indicates the slot ID.";
    }
  }
  notification unequipped-hp {
    description
      "This object indicates that an alarm is generated when the higher order path (HP) is unequipped.";
    leaf card-id {
      type uint32;
      description
        "Indicates the card ID.";
    }
    leaf hp-id {
      type uint32;
      description
        "Indicates the higher order path ID.";
    }
    leaf port-name {
      type string {
        length "1..32";
      }
      description
        "Indicates the physical port name.";
    }
    leaf port-id {
      type uint32;
      description
        "Indicates the port ID.";
    }
    leaf slot-id {
      type uint32;
      description
        "Indicates the slot ID.";
    }
  }
  notification unequipped-hp-resume {
    description
      "This object indicates that a clear alarm is generated when the higher order path (HP) is equipped.";
    leaf card-id {
      type uint32;
      description
        "Indicates the card ID.";
    }
    leaf hp-id {
      type uint32;
      description
        "Indicates the higher order path ID.";
    }
    leaf port-name {
      type string {
        length "1..32";
      }
      description
        "Indicates the physical port name.";
    }
    leaf port-id {
      type uint32;
      description
        "Indicates the port ID.";
    }
    leaf slot-id {
      type uint32;
      description
        "Indicates the slot ID.";
    }
  }
  notification remote-defect {
    description
      "The peer end was faulty.";
    leaf physical-port-index {
      type uint32;
      description
        "Indicates the physical port index.";
    }
    leaf port-name {
      type string {
        length "1..32";
      }
      description
        "Indicates the physical port name.";
    }
  }
  notification remote-defect-resume {
    description
      "The peer end recovered from faults.";
    leaf physical-port-index {
      type uint32;
      description
        "Indicates the physical port index.";
    }
    leaf port-name {
      type string {
        length "1..32";
      }
      description
        "Indicates the physical port name.";
    }
  }
  notification remote-fault {
    description
      "This object indicates that an alarm is generated when the transmit link from the remote device to the local device fails.";
    leaf physical-port-index {
      type uint32;
      description
        "Indicates the physical port index.";
    }
    leaf port-name {
      type string {
        length "1..32";
      }
      description
        "Indicates the physical port name.";
    }
  }
  notification remote-fault-resume {
    description
      "This object indicates that a clear alarm is generated when the transmit link from the remote device to the local device recovers.";
    leaf physical-port-index {
      type uint32;
      description
        "Indicates the physical port index.";
    }
    leaf port-name {
      type string {
        length "1..32";
      }
      description
        "Indicates the physical port name.";
    }
  }
  notification ms-b2-degrade {
    description
      "This object indicates the signal degrade in the multiplex section B2.";
    leaf card-id {
      type uint32;
      description
        "Indicates the card ID.";
    }
    leaf port-name {
      type string {
        length "1..32";
      }
      description
        "Indicates the physical port name.";
    }
    leaf port-id {
      type uint32;
      description
        "Indicates the port ID.";
    }
    leaf slot-id {
      type uint32;
      description
        "Indicates the slot ID.";
    }
  }
  notification ms-b2-degrade-resume {
    description
      "This object indicates that the alarm for the signal degrade in the multiplex section B2 is cleared.";
    leaf card-id {
      type uint32;
      description
        "Indicates the card ID.";
    }
    leaf port-name {
      type string {
        length "1..32";
      }
      description
        "Indicates the physical port name.";
    }
    leaf port-id {
      type uint32;
      description
        "Indicates the port ID.";
    }
    leaf slot-id {
      type uint32;
      description
        "Indicates the slot ID.";
    }
  }
  notification section-alignment {
    description
      "This object indicates that an alarm is generated when the section frame alignment between the local and remote ends is incorrect.";
    leaf card-id {
      type uint32;
      description
        "Indicates the card ID.";
    }
    leaf port-name {
      type string {
        length "1..32";
      }
      description
        "Indicates the physical port name.";
    }
    leaf port-id {
      type uint32;
      description
        "Indicates the port ID.";
    }
    leaf slot-id {
      type uint32;
      description
        "Indicates the slot ID.";
    }
  }
  notification section-alignment-resume {
    description
      "This object indicates that a clear alarm is generated when the section frame alignment error between the local and remote ends is corrected.";
    leaf card-id {
      type uint32;
      description
        "Indicates the card ID.";
    }
    leaf port-name {
      type string {
        length "1..32";
      }
      description
        "Indicates the physical port name.";
    }
    leaf port-id {
      type uint32;
      description
        "Indicates the port ID.";
    }
    leaf slot-id {
      type uint32;
      description
        "Indicates the slot ID.";
    }
  }
  notification tim-trace-mismatch {
    description
      "This object indicates that an alarm is generated when TIM trace identifiers between the local and remote ends mismatch.";
    leaf card-id {
      type uint32;
      description
        "Indicates the card ID.";
    }
    leaf port-name {
      type string {
        length "1..32";
      }
      description
        "Indicates the physical port name.";
    }
    leaf port-id {
      type uint32;
      description
        "Indicates the port ID.";
    }
    leaf slot-id {
      type uint32;
      description
        "Indicates the slot ID.";
    }
  }
  notification tim-trace-mismatch-resume {
    description
      "This object indicates that a clear alarm is generated when TIM trace identifiers between the local and remote ends match.";
    leaf card-id {
      type uint32;
      description
        "Indicates the card ID.";
    }
    leaf port-name {
      type string {
        length "1..32";
      }
      description
        "Indicates the physical port name.";
    }
    leaf port-id {
      type uint32;
      description
        "Indicates the port ID.";
    }
    leaf slot-id {
      type uint32;
      description
        "Indicates the slot ID.";
    }
  }
}
